;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
(DEFUN YARD_STRUCTURE_INFO_GPS (ENT_NAME	 /	      ENTINFO
			    TEMP_ELE1	 TEMP_ELE2    TEMP_ELE3
			    TEMP_ELE4	 FINAL_LIST   EFFNAME
			   )
  (SETQ	TEMP_ELE1 NIL
	TEMP_ELE2 NIL
	TEMP_ELE3 NIL
	TEMP_ELE4 NIL
	TEMP_ELE5 NIL
	TEMP_ELE6 NIL
  )
  (SETQ ENTINFO (ENTGET ENT_NAME))
  (SETQ TEMP_ELE1 (LIST 1 ENT_NAME))
  (SETQ	TEMP_ELE2 (LIST	2
			(VLAX-GET-PROPERTY
			  (VLAX-ENAME->VLA-OBJECT ENT_NAME)
			  "EFFECTIVENAME"
			)
		  )
  )
  (SETQ FLIPLIST (GET_FLIPSTATES_GPS ENT_NAME (NTH 1 TEMP_ELE2)))
  (SETQ TEMP_ELE3 (LIST 3 (CDR (ASSOC 10 ENTINFO))))
  (SETQ	TEMP_ELE4 (LIST	4
			(MERGE_FLIPSTATES
			  (GET_ATTRIBUTES ENT_NAME)
			  (NTH 1 FLIPLIST)
			)
		  )
  )

  (SETQ TEMP_ELE5 (LIST 5 (NTH 0 FLIPLIST)))
  (IF(OR (OR (= (NTH 1 TEMP_ELE2) "PORTAL")
	     (= (NTH 1 TEMP_ELE2) "TTC")
	 )
	 (= (NTH 1 TEMP_ELE2) "SS4")
     )

     
    (SETQ TEMP_ELE6
	   (LIST 6
		 (GET_CANTILEVERS
		   (NTH 1 TEMP_ELE3)
		   (NTH 1 TEMP_ELE2)
		   ENT_NAME
		 )
	   )
    )
    (SETQ TEMP_ELE6 (LIST 6 NIL))
  )
  (SETQ	FINAL_LIST
	 (LIST TEMP_ELE1 TEMP_ELE2 TEMP_ELE3 TEMP_ELE4 TEMP_ELE5
	       TEMP_ELE6)
  )
)


;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;

(DEFUN DATA_COLLECT_GPS (ENTITY_LIST	 BLOCK_FILTER_LIST
			   OUTPUT_DFX1	 OUTPUT_DFX2 /	BLOCK_NAME_LIST	 I
			   TEMP_ENAME	  ENT_OBJECT	 SAFEARRAY_NAME
			   ENT_OBJECT_NAME		 TEMP_ELE TEMP_ELE1 ATTRIBUTE_SET SS_SET
			  )
  (SETQ BLOCK_NAME_LIST (EXTRACT_ENTITY_INFO2 ENTITY_LIST))
  (SETQ BLOCK_NAME_LIST (SINGLE_ELE_LIST (FILTER_LIST BLOCK_FILTER_LIST BLOCK_NAME_LIST 1) 0))
  (SETQ I 0)(SETQ TEMP_ELE NIL)
  (SETQ ATTRIBUTE_SET NIL)
  (WHILE (< I (LENGTH BLOCK_NAME_LIST))
    (IF	(OR (= OUTPUT_DFX1 66) (= OUTPUT_DFX1 2))
      (PROGN (SETQ TEMP_ENAME (NTH I BLOCK_NAME_LIST))
	     (SETQ ENT_OBJECT (VLAX-ENAME->VLA-OBJECT TEMP_ENAME))
	    (IF (= OUTPUT_DFX1 66)(PROGN (SETQ SAFEARRAY_NAME
		    (VLAX-SAFEARRAY->LIST
		      (VLAX-VARIANT-VALUE
			(VLAX-INVOKE-METHOD ENT_OBJECT 'GetAttributes)
		      )
		    )
	     )
	     (SETQ ENT_OBJECT_NAME
		    (VLAX-GET-PROPERTY
		      (NTH 0 SAFEARRAY_NAME)
		      "TEXTSTRING"
		    )
	     ))(PROGN (SETQ ENT_OBJECT_NAME (VLAX-GET-PROPERTY ENT_OBJECT 'EFFECTIVENAME)))
      ))
      (PROGN
	(SETQ ENT_OBJECT_NAME
	       (CDR (ASSOC OUTPUT_DFX1
			   (ENTGET (NTH I BLOCK_NAME_LIST))
		    )
	       )
	)
      )
    )
    (SETQ TEMP_ELE
	   (CDR (ASSOC OUTPUT_DFX2 (ENTGET (NTH I BLOCK_NAME_LIST))))
    )
    (SETQ TEMP_ELE1 (LIST ENT_OBJECT_NAME TEMP_ELE))
(SETQ ATTRIBUTE_SET (CONS TEMP_ELE1 ATTRIBUTE_SET))
    (SETQ I (+ I 1))
    
  )ATTRIBUTE_SET
)



(DEFUN YARD_DATA_COLLECT_GPS (ENTITY_LIST BLOCKNAME_LIST J K / LIST1 I TEMP_ELE TEMP_LIST LIST2)

  (SETQ LIST1 (SINGLE_ELE_LIST (FILTER_LIST BLOCKNAME_LIST (DATA_COLLECT_GPS ENTITY_LIST BLOCKNAME_LIST 2 -1)  0) 1))
  (SETQ I 0)
  (SETQ TEMP_ELE NIL)
  (SETQ TEMP_LIST NIL)
  (SETQ LIST2 NIL)
  (WHILE (< I (LENGTH LIST1))
    (SETQ TEMP_LIST (YARD_STRUCTURE_INFO_GPS (NTH I LIST1)))
  (SETQ TEMP_ELE (LIST (NTH 1 (ASSOC J  TEMP_LIST)) (NTH 1 (ASSOC K  TEMP_LIST))))
  (SETQ LIST2 (CONS TEMP_ELE LIST2))
    (SETQ I (+ I 1))
    )
  (REVERSE LIST2)
)

;                                                                                                                                                                  ;
;                                                Modifiled flip logic determination function                                                                       ;
;                                                                                                                                                                  ;

(DEFUN GET_FLIPSTATES_GPS (ENTNAME BLKNAME / DN_ORIENTATION_STRUCTURES UP_ORIENTATION_STRUCTURES STRUCTURES_WITH_STAGGERS TEMP_ELE TEMP_ELE1 LIST2 STF ANF SGM_X J )
  (SETQ STRUCTURES (LIST "SINGLE_CANT_MAST" "SINGLE_CANT_DA" "SINGLE_CANT_UPRIGHT"  "SS1" "BOX_TYPE" "SPS" "DOUBLE_CANT_MAST"  "DOUBLE_CANT_DA" "TRIPLE_CANT_MAST"  "TRIPLE_CANT_DA" "SS2" "SS3" "DOUBLE_CANT_UPRIGHT" "TRIPLE_CANT_UPRIGHT" "TTC" "SS4"))
  (SETQ STRUCTURES_WITH_STAGGERS (LIST "SINGLE_CANT_MAST" "SINGLE_CANT_DA" "SS1" "BOX_TYPE" "DOUBLE_CANT_MAST"  "DOUBLE_CANT_DA" "TRIPLE_CANT_MAST"  "TRIPLE_CANT_DA" "SS2" "SS3" "SINGLE_CANT_UPRIGHT" "DOUBLE_CANT_UPRIGHT" "TRIPLE_CANT_UPRIGHT"))
  (SETQ TEMP_ELE NIL TEMP_ELE1 NIL LIST2 NIL)
  ;(SETQ BLKNAME (VLAX-GET-PROPERTY (VLAX-ENAME->VLA-OBJECT ENTNAME) "EFFECTIVENAME"))
  (SETQ STF (ASSOC "STF1" (GET_DYNAMIC_PROPERTIES ENTNAME (LIST "STF1"))))
  (SETQ ANF (ASSOC "ANF1" (GET_DYNAMIC_PROPERTIES ENTNAME (LIST "ANF1"))))
  (IF (/= STF NIL) (SETQ STF (NTH 1 STF)))
  (IF (/= ANF NIL) (SETQ ANF (NTH 1 ANF)))
  (IF (/= STF NIL)
  (PROGN 
  (IF (/= (VL-POSITION BLKNAME STRUCTURES) NIL)
    (PROGN (IF (= STF 0) (SETQ TEMP_ELE1 "DN") (SETQ TEMP_ELE1 "UP")))
  )
  
  
  )
  )
  (IF (/= ANF NIL)
  (PROGN (IF (= BLKNAME "ANCHOR")
    (PROGN (IF (= ANF 0) (SETQ TEMP_ELE1 "START") (SETQ TEMP_ELE1 "END")))
  ))
  )
  (IF (/= (VL-POSITION BLKNAME STRUCTURES_WITH_STAGGERS) NIL)
  (PROGN (SETQ SGF (GET_DYNAMIC_PROPERTIES ENTNAME (LIST "SGF1" "SGF2" "SGF3")))
         (SETQ SGM_X (GET_DYNAMIC_PROPERTIES ENTNAME (LIST "SGM1 X" "SGM2 X" "SGM3 X")))
         (SETQ  J 0)
         (WHILE (< J (LENGTH SGF))
	   (SETQ TEMP_ELE (LIST (NTH 1 (ASSOC (STRCAT "SGF" (ITOA (+ J 1))) SGF)) (NTH 1 (ASSOC (STRCAT "SGM" (ITOA (+ J 1)) " " "X") SGM_X))))
	   (SETQ LIST2 (CONS TEMP_ELE LIST2))
	   (SETQ J (+ J 1))
	 ))
  )
  (IF (/=  LIST2 NIL) 
    (SETQ LIST2 (MAP_ELEMENTS (SINGLE_ELE_LIST (SORT_FUN LIST2 0 1) 0) (LIST 0 1) (LIST "DN" "UP")))
  )
  (LIST TEMP_ELE1 LIST2)
)

;                                                                                                                                                                     ;
;                                              Modifiled flip logic determination function ends                                                                       ;
;                                                                                                                                                                     ;










(DEFUN DISTANCE_ON_CURVE_GPS ( POLYLINE_ENTITY POINT1 POINT2 / TEMP_DISTANCE1 TEMP_DISTANCE2  )
  (SETQ TEMP_DISTANCE1 (VLAX-CURVE-GETDISTATPOINT POLYLINE_ENTITY POINT1))
  (SETQ TEMP_DISTANCE2 (VLAX-CURVE-GETDISTATPOINT POLYLINE_ENTITY POINT2))
(ABS (- TEMP_DISTANCE1 TEMP_DISTANCE2))
)



(DEFUN SORT_ENTITIES_ALONG_CURVE (POLYLINE_ENTITY LIST1 STARTING_ENTITY FLAG1 FLAG2 / I TEMP_ELE1 TEMP_ELE2 FINAL_LIST)
   (SETQ I 0 TEMP_ELE1 NIL TEMP_ELE2 NIL FINAL_LIST NIL)
   (WHILE (< I (LENGTH LIST1))
     (SETQ TEMP_ELE1 (DISTANCE_ON_CURVE_GPS POLYLINE_ENTITY (NTH FLAG1 (NTH I LIST1)) (NTH FLAG2 STARTING_ENTITY)))
     (SETQ TEMP_ELE2 (LIST TEMP_ELE1 (NTH I LIST1)))
     (SETQ FINAL_LIST (CONS TEMP_ELE2 FINAL_LIST))
     (SETQ I (+ I 1))
   )
   (SINGLE_ELE_LIST (SORT_FUN FINAL_LIST 0 0) 1)
 )




(DEFUN SORT_ENTITIES_ALONG_CURVE1 (POLYLINE_ENTITY LIST1 STARTING_ENTITY FLAG1 FLAG2 / I TEMP_ELE1 TEMP_ELE2 FINAL_LIST)
   (SETQ I 0 TEMP_ELE1 NIL TEMP_ELE2 NIL FINAL_LIST NIL)
   (WHILE (< I (LENGTH LIST1))
     (SETQ TEMP_ELE1 (DISTANCE_ON_CURVE_GPS POLYLINE_ENTITY (VLAX-CURVE-GETCLOSESTPOINTTO POLYLINE_ENTITY (CDR (ASSOC 10 (ENTGET (NTH FLAG1 (NTH I LIST1))))) T) (NTH FLAG2 STARTING_ENTITY)))
     (SETQ TEMP_ELE2 (LIST TEMP_ELE1 (NTH I LIST1)))
     (SETQ FINAL_LIST (CONS TEMP_ELE2 FINAL_LIST))
     (SETQ I (+ I 1))
   )
   (SINGLE_ELE_LIST (SORT_FUN FINAL_LIST 0 0) 1)
 )





  
(DEFUN SORT_MASTS_NEW (ENT_LIST STARTING_KM_STONE FLAG1 FLAG2 / I TEMP_DIST FINAL_LIST )
  (SETQ I 0 TEMP_DIST NIL FINAL_LIST NIL)
  (WHILE (< I (LENGTH ENT_LIST))
    (SETQ TEMP_DIST (DISTANCE (NTH FLAG2 STARTING_KM_STONE) (NTH FLAG1 (NTH I ENT_LIST))))
    (SETQ FINAL_LIST (CONS (LIST (NTH I ENT_LIST) (LIST TEMP_DIST)) FINAL_LIST))
    (SETQ I (+ I 1))
  )
  (SINGLE_ELE_LIST (SORT_FUN (REVERSE FINAL_LIST) 0 2) 0)
)

(DEFUN UPDATE_TOTAL_CHAINAGES_SPLIT_GPS (KM_LIST UPLIST DNLIST POLYLINE_ENTITY / I TEMP_ELE1 TEMP_ELE2 TEMP_ELE3 F LOC_NO ST_CH ENT_LIST TEMP_KM ST_CH_UP ST_CH_DN)
     (SETQ F 0 TEMP_ELE1 NIL TEMP_ELE2 NIL TEMP_ELE3 NIL TEMP_KM NIL)
   (setq dcl_id (load_dialog "DISPLAY_INFO.dcl"))
   (new_dialog "DISPLAY_INFO" dcl_id)
  (WHILE (< F (LENGTH KM_LIST))
    (SETQ TEMP_ELE1 (NTH F KM_LIST) TEMP_ELE2 (NTH F UPLIST) TEMP_ELE3 (NTH F DNLIST) TEMP_ELE4 (NTH (+ F 1) KM_LIST))
     (SET_TILE "INFO" (STRCAT "UPDATING KM " (ITOA (+ F 1)) " OF "  (ITOA (LENGTH KM_LIST))))
     (SET_TILE "PERCENTAGE" (STRCAT (RTOS (/ (* (+ F 1) 100) (ATOF (RTOS (LENGTH KM_LIST) 2 2)) ) 2 2) "%" "COMPLETED"))
    (IF (= F (- (LENGTH KM_LIST) 1))
      (PROGN
      (SET_TILE "INFO" (STRCAT "ALL " "KILOMETER" " LOCATIONS ARE UPDATED SUCESSFULLY"))
      (SET_TILE "PERCENTAGE" "PRESS OK TO CONTINUE")
      )
    )
    
    (SETQ ATTR_LIST (GET_ATTRIBUTES (NTH 0 TEMP_ELE1)))
    (SETQ TEMP_KM (NTH 1 (ASSOC "KM" ATTR_LIST)))
    (SETQ TEMP_KM (SUBSTR TEMP_KM (+ (VL-STRING-POSITION (ASCII ":") TEMP_KM) 2)))

    (IF (/= TEMP_ELE4 NIL)
    (PROGN
    (SETQ ATTR_LIST1 (GET_ATTRIBUTES (NTH 0 TEMP_ELE4)))
    (SETQ TEMP_KM1 (NTH 1 (ASSOC "KM" ATTR_LIST1)))
    (SETQ TEMP_KM1 (SUBSTR TEMP_KM1 (+ (VL-STRING-POSITION (ASCII ":") TEMP_KM1) 2)))
    )
    )
    
    ;(SETQ TEMP_ELE2 (SORT_MASTS_NEW TEMP_ELE2 TEMP_ELE1 1 2))
    ;(SETQ TEMP_ELE3 (SORT_MASTS_NEW TEMP_ELE3 TEMP_ELE1 1 2))
    ;(SETQ LOC_NO (STRCAT (NTH 0 TEMP_ELE1) "/" STARTING_LOCATION))
    ;(VLAX-CURVE-GETCLOSESTPOINTTO POLYLINE_ENTITY (NTH 1 (NTH 0 TEMP_ELE3)) T)
    (IF (= F 0)
    (PROGN
    (SETQ ST_CH_UP (STRCAT TEMP_KM "/" (RTOS (DISTANCE_ON_CURVE_GPS  POLYLINE_ENTITY (NTH 2 TEMP_ELE1) (NTH 1 (NTH 0 TEMP_ELE2))) 2 2)))
    (SETQ ST_CH_DN (STRCAT TEMP_KM "/" (RTOS (DISTANCE_ON_CURVE_GPS  POLYLINE_ENTITY (NTH 2 TEMP_ELE1) (NTH 1 (NTH 0 TEMP_ELE3))) 2 2)))
    )
    )
    
    (SETQ TEMP_ELE2 (UPDATE_CHAINAGES_SPLIT_GPS ST_CH_UP TEMP_ELE2 "DN"))
    (SETQ TEMP_ELE3 (UPDATE_CHAINAGES_SPLIT_GPS ST_CH_DN TEMP_ELE3 "UP"))
    (SETQ END_CH_UP (NTH 0 (NTH 1 (NTH (- (LENGTH TEMP_ELE2) 1) TEMP_ELE2))) END_SPAN_UP (NTH 2 (NTH 1 (NTH (- (LENGTH TEMP_ELE2) 1) TEMP_ELE2))))
    (SETQ END_CH_DN (NTH 0 (NTH 1 (NTH (- (LENGTH TEMP_ELE3) 1) TEMP_ELE3))) END_SPAN_DN (NTH 2 (NTH 1 (NTH (- (LENGTH TEMP_ELE3) 1) TEMP_ELE3))))
    (SETQ ST_CH_UP  (- END_SPAN_UP (- 1000 END_CH_UP)))
    (SETQ ST_CH_DN  (- END_SPAN_DN (- 1000 END_CH_DN)))
    (IF (/= TEMP_ELE4 NIL)
    (PROGN
    (SETQ ST_CH_UP (STRCAT TEMP_KM1 "/" (RTOS ST_CH_UP 2 2)))
    (SETQ ST_CH_DN (STRCAT TEMP_KM1 "/" (RTOS ST_CH_DN 2 2)))
    )
    )
    (SETQ TEMP_MAIN_LIST (ASSIGN_LOCATION_NUMBERS (SORT_MULTILEVEL (APPEND (ADD_LISTS TEMP_ELE2 (N_ELE_LIST "DN" (LENGTH TEMP_ELE2))) (ADD_LISTS TEMP_ELE3 (N_ELE_LIST "UP" (LENGTH TEMP_ELE3)))) 1 0 1)))
    (UPDATE_LOC_NUMBERS_GPS TEMP_MAIN_LIST TEMP_KM)
    (SETQ F (+ F 1))
  )
  (setq ddiag(start_dialog))
)



(DEFUN UPDATE_LOC_NUMBERS_GPS ( ENT_LIST KM / SSSET ENT_LIST I)
  (SETQ I 0)
  (WHILE (< I (LENGTH ENT_LIST))
    (MODIFY_ATTRIBUTES (NTH 0 (NTH I ENT_LIST)) (LIST "MAST_NUMBER1" "MAST_NUMBER_LINK1") (LIST (STRCAT KM "/" (NTH 3 (NTH I ENT_LIST))) (STRCAT KM "/" (NTH 3 (NTH I ENT_LIST)))))
    (SETQ I (+ I 1))
  )
)





(DEFUN FIND_IN_BETWEEN_GPS (LIST1 LIST2 POLYLINE_ENTITY A B STARTING_ENTITY / I FINAL_LIST TEMP_ELE1 TEMP_ELE2 J TEMP_LIST TEMP_ELE3)
  (SETQ I 1 FINAL_LIST NIL)
  (WHILE (< I (LENGTH LIST1))
    (SETQ TEMP_ELE1 (NTH A (NTH (- I 1) LIST1)) TEMP_ELE2 (NTH A (NTH I LIST1)))
    (SETQ J 0 TEMP_LIST NIL)
    (WHILE (< J (LENGTH LIST2))
      (SETQ TEMP_ELE3 (NTH B (NTH J LIST2)))
      
        (SETQ TEMP_DISTANCE1 (ABS (VLAX-CURVE-GETDISTATPOINT POLYLINE_ENTITY TEMP_ELE1)))
        (SETQ TEMP_DISTANCE2 (ABS (VLAX-CURVE-GETDISTATPOINT POLYLINE_ENTITY TEMP_ELE2)))
        (SETQ TEMP_DISTANCE3 (ABS (VLAX-CURVE-GETDISTATPOINT POLYLINE_ENTITY TEMP_ELE3)))
      
      (IF (OR (AND (> TEMP_DISTANCE3 TEMP_DISTANCE1) (< TEMP_DISTANCE3 TEMP_DISTANCE2))
	  (AND (< TEMP_DISTANCE3 TEMP_DISTANCE1) (> TEMP_DISTANCE3 TEMP_DISTANCE2)))
      (SETQ TEMP_LIST (CONS (NTH J LIST2) TEMP_LIST)))
      
      (SETQ J (+ J 1))
    )
    (IF (/= TEMP_LIST NIL) (SETQ FINAL_LIST (CONS (LIST (SORT_ENTITIES_ALONG_CURVE1 POLYLINE_ENTITY TEMP_LIST STARTING_ENTITY 0 2) (NTH 0 (NTH 0 (SORT_ENTITIES_ALONG_CURVE1 POLYLINE_ENTITY TEMP_LIST STARTING_ENTITY 0 2)))) FINAL_LIST)))
    (SETQ I (+ I 1))
  )
  (REVERSE FINAL_LIST)
)



(DEFUN UPDATE_CHAINAGES_SPLIT_GPS (ST_CH ENT_LIST FLAG / I SSSET LOC_NO ST_CH LOC_NUM_LIST ENT_LIST FINAL_LIST BS_PT BS_PT1 ENT_INFO VALUES VALUES1 VALUES2 VALUES3 VALUES4 FDN_REFERENCE FDN_REFERENCE_X FDN_REFERENCE_Y RD_REFERENCE RD_REFERENCE_X RD_REFERENCE_Y TC_REFERENCE TC_REFERENCE_X TC_REFERENCE_Y SPAN_REFERENCE_X SPAN_REFERENCE_Y ENT_LIST_SPAN POINT POINT1 POINT2 POINT3 ENT_LIST_SPAN VISIBILITY_SPAN VISIBILITY_TC VISIBILITY_FDN VISIBILITY_RD I LOC CH TEMP_ELE SCALE POINT_FDN POINT_RD POINT_TC TEMP_SPAN)

  (SETQ	KM_NO (SUBSTR ST_CH 1 (VL-STRING-POSITION (ASCII "/") ST_CH)))

  (SETQ	ST_CH	(SUBSTR	ST_CH (+ (VL-STRING-POSITION (ASCII "/") ST_CH) 2)))
  ;(SETQ LOC_NUM_LIST (SINGLE_ELE_LIST ENT_LIST 1))
  (IF (= FLAG "DN") (SETQ FLAG1 1) (SETQ FLAG1 0))

  (SETQ I 0 FINAL_LIST NIL)

  (WHILE (< I (LENGTH ENT_LIST))

    (SETQ CH (STRCAT KM_NO "/" ST_CH))
    (SETQ TEMP_ELE  (NTH I ENT_LIST))
    
    (IF (/= (NTH 2 TEMP_ELE) NIL)
    (PROGN
    (MODIFY_ATTRIBUTES (NTH 0 TEMP_ELE) (LIST "CHAINAGE1") (LIST CH))

    (SETQ TEMP_SPAN (* (ATOF (NTH 2 TEMP_ELE)) 1))
    
    (IF (= TEMP_SPAN 0) (SETQ I (LENGTH ENT_LIST)))
    
    (SETQ FINAL_LIST (CONS (LIST (NTH 0 TEMP_ELE) (LIST (ATOF ST_CH) FLAG1 (ATOF (NTH 2 TEMP_ELE)))) FINAL_LIST))
								      
    (SETQ ST_CH (RTOS (+ (ATOF ST_CH) (ATOF (NTH 2 TEMP_ELE))) 2 2))
    )
    )
    (SETQ I (+ I 1))
  )
  (REVERSE FINAL_LIST)
)






(DEFUN GET_PROJECTION_FROM_POINT_LIST_FINAL (LINE_ENTITY POINT_LIST FLAG  / VLA_LINE_ENTITY I TEMP_ELE FINAL_LIST)
(SETQ VLA_LINE_ENTITY (VLAX-ENAME->VLA-OBJECT LINE_ENTITY))
(SETQ I 0 TEMP_ELE NIL FINAL_LIST NIL)
(WHILE (< I (LENGTH POINT_LIST))
(SETQ TEMP_ELE (VLAX-CURVE-GETCLOSESTPOINTTO LINE_ENTITY (NTH FLAG (NTH I POINT_LIST)) T))
(SETQ FINAL_LIST (CONS (LIST (NTH I POINT_LIST) TEMP_ELE) FINAL_LIST))
(SETQ I (+ I 1))
)
(REVERSE FINAL_LIST)
)





(DEFUN C:DRAW_PEGGINGPLAN_GPS ( / TEMP_ELE1 TEMP_ELE2 )
  ;(SETQ WPT1 (GETPOINT "ENTER STARTING POINT IN LOP"))
  ;(SETQ WPT2 (GETPOINT "\n ENTER ENDING POINT IN LOP"))
  (SETQ BLOCKS_LIST (FORM_SSSET (SSGET "X" (LIST (CONS 0 "INSERT")))))
  (SETQ BLOCK_NAME_LIST (EXTRACT_ENTITY_INFO2 BLOCKS_LIST))
  (SETQ KM_STONE_LIST (FILTER_LIST (LIST "KM_NEW" "KM_STONE" "KMNEW" "KMSTONE") BLOCK_NAME_LIST 1))
  (SETQ KM_STONE_LIST (SORT_FUN (ENTITY_DFX (SINGLE_ELE_LIST KM_STONE_LIST 0) 10 -1) 1 0))
  
  
  (SETQ SCALE (GETREAL "\nENTER SCALE : "))
  (PROMPT "SELECT OFFSETS (OFFSET COLOUR CODE : GREEN->SINGLE CANTILEVER YELLOW->DOUBLE CANTILEVER")
  (SETQ OFFSET_ENTITIES1 (SSGET))
  (SETQ OFFSET_ENTITIES2 (SSGET))
  (SETQ STARTING_OFFSET_UP (CAR(ENTSEL "\nSELECT STARTING OFFSET FOR UP TRACK : ")))
  (SETQ STARTING_OFFSET_DN (CAR(ENTSEL "\nSELECT STARTING OFFSET FOR DN TRACK : ")))
  (PROMPT "\nSELECT TRACK ALIGNMENT FOR UP TRACK:")
  (SETQ TRACK_ENTITY_UPTRACK (FORM_SSSET(SSGET)))
  (PROMPT "\nSELECT TRACK ALIGNMENT FOR DN TRACK:")
  (SETQ TRACK_ENTITY_DNTRACK (FORM_SSSET(SSGET)))
  (SETQ ENTNAME_UPTRACK (CAR(ENTSEL "\nSELECT REFERENCE MAST FOR UP TRACK:")))
  (SETQ ENTNAME_DNTRACK (CAR(ENTSEL "\nSELECT REFERENCE MAST FOR DN TRACK:")))
  (SETQ TEMP_ELE1 NIL TEMP_ELE2 NIL)
  (SETQ TEMP_ELE1 (VLAX-SAFEARRAY->LIST (VLAX-VARIANT-VALUE (VLA-INTERSECTWITH (VLAX-ENAME->VLA-OBJECT (NTH 0 TRACK_ENTITY_UPTRACK)) (VLAX-ENAME->VLA-OBJECT STARTING_OFFSET_UP) ACEXTENDNONE))))
  (SETQ TEMP_ELE2 (LIST (NTH 0 TEMP_ELE1) (NTH 1 TEMP_ELE1) (NTH 2 TEMP_ELE1)))
  (IF (/= (VLAX-CURVE-GETDISTATPOINT (NTH 0 TRACK_ENTITY_UPTRACK) TEMP_ELE2)  NIL)
    (SETQ TEMP_ELE1 TEMP_ELE2)
    (SETQ TEMP_ELE1 (LIST (NTH 3 TEMP_ELE1) (NTH 4 TEMP_ELE1) (NTH 5 TEMP_ELE1)))
  )

  (SETQ KM_STONE_COORDINATES (COMBINE_LIST_ELEMENTS (GET_PROJECTION_FROM_POINT_LIST_FINAL (NTH 0 TRACK_ENTITY_UPTRACK) (BUILD_LIST KM_STONE_LIST (LIST 0 1)) 1)))
  (SETQ KM_STONE_COORDINATES (SORT_ENTITIES_ALONG_CURVE (NTH 0 TRACK_ENTITY_UPTRACK) KM_STONE_COORDINATES (LIST STARTING_OFFSET_UP TEMP_ELE1) 2 1))
  
  (SETQ UPLINE_MASTS (INSERT_MASTS_NORMAL_GPS OFFSET_ENTITIES1 STARTING_OFFSET_UP TRACK_ENTITY_UPTRACK SCALE ENTNAME_UPTRACK))
  (SETQ DNLINE_MASTS (INSERT_MASTS_DN_NORMAL_GPS OFFSET_ENTITIES2 STARTING_OFFSET_DN TRACK_ENTITY_DNTRACK SCALE ENTNAME_DNTRACK))
  
  (SETQ UPLINE_MAST_ENTITIES (BUILD_LIST (COMBINE_LIST_ELEMENTS (GET_PROJECTION_FROM_POINT_LIST_FINAL (NTH 0 TRACK_ENTITY_UPTRACK) (ADD_LISTS UPLINE_MASTS (N_ELE_LIST "DN" (LENGTH UPLINE_MASTS))) 1)) (LIST 0 4 2 3)))
  (SETQ DNLINE_MAST_ENTITIES (BUILD_LIST (COMBINE_LIST_ELEMENTS (GET_PROJECTION_FROM_POINT_LIST_FINAL (NTH 0 TRACK_ENTITY_UPTRACK) (ADD_LISTS DNLINE_MASTS (N_ELE_LIST "UP" (LENGTH DNLINE_MASTS))) 1)) (LIST 0 4 2 3)))
  
  (SETQ UPLINE_MASTS (FIND_IN_BETWEEN_GPS KM_STONE_COORDINATES UPLINE_MAST_ENTITIES (NTH 0 TRACK_ENTITY_UPTRACK) 2 1 (NTH 0 KM_STONE_COORDINATES)))
  (SETQ DNLINE_MASTS (FIND_IN_BETWEEN_GPS KM_STONE_COORDINATES DNLINE_MAST_ENTITIES (NTH 0 TRACK_ENTITY_UPTRACK) 2 1 (NTH 0 KM_STONE_COORDINATES)))

  
  (UPDATE_TOTAL_CHAINAGES_SPLIT_GPS  (VL-REMOVE (NTH (- (LENGTH KM_STONE_COORDINATES) 1) KM_STONE_COORDINATES) KM_STONE_COORDINATES) (SINGLE_ELE_LIST (SORT_ENTITIES_ALONG_CURVE1 (NTH 0 TRACK_ENTITY_UPTRACK) UPLINE_MASTS (NTH 0 KM_STONE_COORDINATES) 1 2) 0) (SINGLE_ELE_LIST (SORT_ENTITIES_ALONG_CURVE1 (NTH 0 TRACK_ENTITY_UPTRACK) DNLINE_MASTS (NTH 0 KM_STONE_COORDINATES) 1 2) 0) (NTH 0 TRACK_ENTITY_UPTRACK))
  ;(UPDATE_TOTAL_CHAINAGES_SPLIT (VL-REMOVE (NTH (- (LENGTH KM_STONE_COORDINATES) 1) KM_STONE_COORDINATES) KM_STONE_COORDINATES) UPLINE_MASTS DNLINE_MASTS SCALE ENTNAME_UPTRACK ENTNAME_DNTRACK)
)


(DEFUN COMBINE_LIST_ELEMENTS (LIST1 / I FINAL_LIST J TEMP_LIST )
  (SETQ I 0 TEMP_LIST NIL FINAL_LIST NIL)
  (WHILE (< I (LENGTH LIST1))
    (SETQ TEMP_LIST (APPEND (NTH 0 (NTH I LIST1)) (LIST (NTH 1 (NTH I LIST1)))))
    (SETQ FINAL_LIST (CONS TEMP_LIST FINAL_LIST))
    (SETQ I (+ I 1))
  )
  (REVERSE FINAL_LIST)
)








(DEFUN INDENTIFY_LOCATIONS_GPS ( SNAP_POINTS TRACK_TYPE / I FINAL_LIST PREV_COLOUR_CODE NEXT_COLOUR_CODE LOC )
  (SETQ I 0)
  (SETQ FINAL_LIST NIL PREV_COLOUR_CODE NIL NEXT_COLOUR_CODE NIL)
  (WHILE (< I (LENGTH SNAP_POINTS))
    (SETQ COLOUR_CODE (CDR (ASSOC 62  (ENTGET (NTH 0 (NTH I SNAP_POINTS))))))
    (IF (/= I 0)
      (SETQ PREV_COLOUR_CODE (CDR (ASSOC 62  (ENTGET (NTH 0 (NTH (- I 1) SNAP_POINTS))))))
      (SETQ PREV_COLOUR_CODE NIL)
    )
    (IF (/= I (- (LENGTH SNAP_POINTS) 1))
      (SETQ NEXT_COLOUR_CODE (CDR (ASSOC 62  (ENTGET (NTH 0 (NTH (+ I 1) SNAP_POINTS))))))
      (SETQ NEXT_COLOUR_CODE NIL)
    )
    (SETQ LOC NIL)
  (IF (= COLOUR_CODE 3)
    (PROGN
    (IF (AND (/= (VL-POSITION PREV_COLOUR_CODE (LIST 2 5 1)) NIL) (/= NEXT_COLOUR_CODE 2))
      (SETQ LOC "BWA_END")
    )
    
    (IF (AND (/= PREV_COLOUR_CODE 2) (/= (VL-POSITION NEXT_COLOUR_CODE (LIST 2 5 1)) NIL))
      (SETQ LOC "BWA_START")
    )

    (IF (/= (VL-POSITION PREV_COLOUR_CODE (LIST 7 8 9)) NIL)
      (SETQ LOC "ACA_END")
    )
    
    (IF (/= (VL-POSITION NEXT_COLOUR_CODE (LIST 7 8 9)) NIL)
      (SETQ LOC "ACA_START")
    )
    
    (IF (AND (= PREV_COLOUR_CODE 3) (= NEXT_COLOUR_CODE 3))
      (SETQ LOC "NORMAL")
    )
    
    )
  )

  (IF (/= (VL-POSITION COLOUR_CODE (LIST 2 5 1)) NIL)
    (PROGN
    (IF (= COLOUR_CODE 2)
      (PROGN
    (IF (AND (/= (VL-POSITION PREV_COLOUR_CODE (LIST 2 5 1)) NIL) (/= (VL-POSITION NEXT_COLOUR_CODE (LIST 2 5 1)) NIL))
      (SETQ LOC "OLC")
      (SETQ LOC "DOUBLE")
    )
      )
    )
    (IF (/= (VL-POSITION COLOUR_CODE (LIST 5 1)) NIL)
      (PROGN
    (IF (AND (/= (VL-POSITION PREV_COLOUR_CODE (LIST 2 5 1)) NIL) (/= (VL-POSITION NEXT_COLOUR_CODE (LIST 2 5 1)) NIL))
      (PROGN
      (IF (= COLOUR_CODE 5)
      (SETQ LOC "OLCAEWA")
      (SETQ LOC "OLCFA")
      ))
      (PROGN
      (IF (= COLOUR_CODE 5)
      (SETQ LOC "DAEWA")
      (SETQ LOC "DFA")
      ))
    )
      )
    )
    )
  )

  (IF (= COLOUR_CODE 7)
  (SETQ LOC "ACC")
  )

  (IF (= COLOUR_CODE 4)
  (SETQ LOC "AEWA")
  )

  (IF (= COLOUR_CODE 6)
  (SETQ LOC "FA")
  )

  (IF (= COLOUR_CODE 8)
  (SETQ LOC "ACCFA")
  )

  (IF (= COLOUR_CODE 9)
  (SETQ LOC "ACCAEWA")
  )
    

 (SETQ FINAL_LIST (CONS LOC FINAL_LIST))
 (SETQ I (+ I 1))
 )
 
 (ADD_LISTS SNAP_POINTS (BUILD_LIST (WIRE_NUMBERING (REVERSE FINAL_LIST) TRACK_TYPE) (LIST 1 2 3)))
 )




(DEFUN GET_OFFSET_INTERSECTION_POINTS ( OFFSET_ENTITIES1 TRACK_ENTITY / OFFSET_ENTITIES TRACK_ENTITY I TEMP_ELE1 TEMP_ELE2 LIST2 )

  (SETQ OFFSET_ENTITIES1 (FORM_SSSET OFFSET_ENTITIES1))
  (SETQ I 0)
  (SETQ OFFSET_ENTITIES NIL)
  (WHILE (< I (LENGTH OFFSET_ENTITIES1))
    (SETQ TEMP_ELE1 (CDR (ASSOC 10 (ENTGET (NTH I OFFSET_ENTITIES1)))))
    (SETQ OFFSET_ENTITIES (CONS (LIST (NTH I OFFSET_ENTITIES1) TEMP_ELE1) OFFSET_ENTITIES))
    (SETQ I (+ I 1))
  )
  (SETQ OFFSET_ENTITIES (REVERSE OFFSET_ENTITIES))
  (SETQ OFFSET_ENTITIES (SORT_FUN OFFSET_ENTITIES 1 0))
  
  (SETQ I 0)
  (SETQ TEMP_ELE1 NIL)
  (SETQ TEMP_ELE2 NIL)
  (SETQ LIST2 NIL)
  (WHILE (< I (LENGTH OFFSET_ENTITIES))
  ;(SETQ TEMP_ELE1 (NTH 0 (ACET-GEOM-INTERSECTWITH TRACK_ENTITY (NTH 0 (NTH I OFFSET_ENTITIES)) 0.0000001)))
  (SETQ TEMP_ELE1 (VLAX-SAFEARRAY->LIST (VLAX-VARIANT-VALUE (VLA-INTERSECTWITH (VLAX-ENAME->VLA-OBJECT TRACK_ENTITY) (VLAX-ENAME->VLA-OBJECT (NTH 0 (NTH I OFFSET_ENTITIES))) ACEXTENDNONE))))
  (SETQ TEMP_ELE2 (LIST (NTH 0 TEMP_ELE1) (NTH 1 TEMP_ELE1) (NTH 2 TEMP_ELE1)))
  (IF (/= (VLAX-CURVE-GETDISTATPOINT TRACK_ENTITY TEMP_ELE2)  NIL)
    (SETQ TEMP_ELE1 TEMP_ELE2)
    (SETQ TEMP_ELE1 (LIST (NTH 3 TEMP_ELE1) (NTH 4 TEMP_ELE1) (NTH 5 TEMP_ELE1)))
  )
  (SETQ LIST2 (CONS (LIST (NTH 0 (NTH I OFFSET_ENTITIES)) TEMP_ELE1) LIST2))
  (SETQ I (+ I 1))
  )
  (SORT_FUN (REVERSE LIST2) 1 0)
)







(DEFUN INSERT_MASTS_NORMAL_GPS ( OFFSET_ENTITIES1 STARTING_OFFSET TRACK_ENTITY SCALE ENTNAME / SNAP_POINTS I TEMP_ELE MAST_LIST INSERTION_POINT MAST_LENGTH VALUES POINT IMP_REFERENCE SG_REFERENCE FLAG MAST_LIST IMP_POINT STAG_POINT SCALE)


(SETQ OS_MODE (GETVAR "OSMODE"))
(SETQ 3DOS_MODE (GETVAR "3DOSMODE"))
(SETVAR "OSMODE" 0)
(SETVAR "3DOSMODE" 0)
(COMMAND "UCS" "W")
(SETQ SNAP_POINTS (SORT_ENTITIES_ALONG_CURVE (NTH 0 TRACK_ENTITY) (GET_OFFSET_INTERSECTION_POINTS OFFSET_ENTITIES1 (NTH 0 TRACK_ENTITY)) (ASSOC STARTING_OFFSET (GET_OFFSET_INTERSECTION_POINTS OFFSET_ENTITIES1 (NTH 0 TRACK_ENTITY))) 1 1))
(SETQ SNAP_POINTS (INDENTIFY_LOCATIONS_GPS SNAP_POINTS "DN"))
(SETQ SNAP_POINTS_SPAN (SPAN_FROM_OFFSETS (NTH 0 TRACK_ENTITY) (BUILD_LIST SNAP_POINTS (LIST 0 1)) 1))
(SETQ INSERTION_POINTS_SPAN (GET_MAST_INSERTION_POINT_GPS_LEFT (NTH 0 TRACK_ENTITY) SNAP_POINTS_SPAN (N_ELE_LIST 3.00 (LENGTH SNAP_POINTS_SPAN)) 1))
(SETQ MAST_LENGTH (GET_DYNAMIC_PROPERTIES ENTNAME '("STL1")))

  (SETQ MAST_NUMBER (GET_TEXT_ALIGNMENT_POINT (LIST ENTNAME) "MAST_NUMBER_LINK1" 0))
  (SETQ MAST_NUMBER_X (- (NTH 0 (NTH 1 (NTH 0 MAST_NUMBER))) (NTH 0 (CDR (ASSOC 10 (ENTGET ENTNAME))))))
  (SETQ MAST_NUMBER_Y (- (NTH 1 (NTH 1 (NTH 0 MAST_NUMBER))) (NTH 1 (CDR (ASSOC 10 (ENTGET ENTNAME))))))
  
  (SETQ TC_REFERENCE (GET_TEXT_ALIGNMENT_POINT (LIST ENTNAME) "TC1" 0))
  (SETQ TC_REFERENCE_X (- (NTH 0 (NTH 1 (NTH 0 TC_REFERENCE))) (NTH 0 (CDR (ASSOC 10 (ENTGET ENTNAME))))))
  (SETQ TC_REFERENCE_Y (- (NTH 1 (NTH 1 (NTH 0 TC_REFERENCE))) (NTH 1 (CDR (ASSOC 10 (ENTGET ENTNAME))))))
  
  (SETQ SPAN_REFERENCE (GET_TEXT_ALIGNMENT_POINT (LIST ENTNAME) "SPAN1" 0))
  (SETQ SPAN_REFERENCE_X (- (NTH 0 (NTH 1 (NTH 0 SPAN_REFERENCE))) (NTH 0 (CDR (ASSOC 10 (ENTGET ENTNAME))))))
  (SETQ SPAN_REFERENCE_Y (- (NTH 1 (NTH 1 (NTH 0 SPAN_REFERENCE))) (NTH 1 (CDR (ASSOC 10 (ENTGET ENTNAME))))))
  
  
  (SETQ FDN_REFERENCE (GET_TEXT_ALIGNMENT_POINT (LIST ENTNAME) "FOUNDATION_TYPE1" 0))
  (SETQ FDN_REFERENCE_X (- (NTH 0 (NTH 1 (NTH 0 FDN_REFERENCE))) (NTH 0 (CDR (ASSOC 10 (ENTGET ENTNAME))))))
  (SETQ FDN_REFERENCE_Y (- (NTH 1 (NTH 1 (NTH 0 FDN_REFERENCE))) (NTH 1 (CDR (ASSOC 10 (ENTGET ENTNAME))))))
  
  (SETQ RD_REFERENCE (GET_TEXT_ALIGNMENT_POINT (LIST ENTNAME) "RD1" 0))
  (SETQ RD_REFERENCE_X (- (NTH 0 (NTH 1 (NTH 0 RD_REFERENCE))) (NTH 0 (CDR (ASSOC 10 (ENTGET ENTNAME))))))
  (SETQ RD_REFERENCE_Y (- (NTH 1 (NTH 1 (NTH 0 RD_REFERENCE))) (NTH 1 (CDR (ASSOC 10 (ENTGET ENTNAME))))))

  (SETQ SD/EL_REFERENCE (GET_TEXT_ALIGNMENT_POINT (LIST ENTNAME) "STEP_DISTANCE/EMBEDDED_LENGTH" 0))
  (SETQ SD/EL_REFERENCE_X (- (NTH 0 (NTH 1 (NTH 0 SD/EL_REFERENCE))) (NTH 0 (CDR (ASSOC 10 (ENTGET ENTNAME))))))
  (SETQ SD/EL_REFERENCE_Y (- (NTH 1 (NTH 1 (NTH 0 SD/EL_REFERENCE))) (NTH 1 (CDR (ASSOC 10 (ENTGET ENTNAME))))))

  (SETQ SB/ED_REFERENCE (GET_TEXT_ALIGNMENT_POINT (LIST ENTNAME) "SUPER_BLOCK/EXTRA_DEPTH" 0))
  (SETQ SB/ED_REFERENCE_X (- (NTH 0 (NTH 1 (NTH 0 SB/ED_REFERENCE))) (NTH 0 (CDR (ASSOC 10 (ENTGET ENTNAME))))))
  (SETQ SB/ED_REFERENCE_Y (- (NTH 1 (NTH 1 (NTH 0 SB/ED_REFERENCE))) (NTH 1 (CDR (ASSOC 10 (ENTGET ENTNAME))))))

  (SETQ AB/AS/ASD_REFERENCE (GET_TEXT_ALIGNMENT_POINT (LIST ENTNAME) "ANCHOR_BLOCK/ANCHOR_STEP/ANCHOR_SETTING_DISTANCE" 0))
  (SETQ AB/AS/ASD_REFERENCE_X (- (NTH 0 (NTH 1 (NTH 0 AB/AS/ASD_REFERENCE))) (NTH 0 (CDR (ASSOC 10 (ENTGET ENTNAME))))))
  (SETQ AB/AS/ASD_REFERENCE_Y (- (NTH 1 (NTH 1 (NTH 0 AB/AS/ASD_REFERENCE))) (NTH 1 (CDR (ASSOC 10 (ENTGET ENTNAME))))))

  (SETQ RADIUS/SUPER_ELEVATION (GET_TEXT_ALIGNMENT_POINT (LIST ENTNAME) "RADIUS/SUPER_ELEVATION" 0))
  (SETQ RADIUS/SUPER_ELEVATION_X (- (NTH 0 (NTH 1 (NTH 0 RADIUS/SUPER_ELEVATION))) (NTH 0 (CDR (ASSOC 10 (ENTGET ENTNAME))))))
  (SETQ RADIUS/SUPER_ELEVATION_Y (- (NTH 1 (NTH 1 (NTH 0 RADIUS/SUPER_ELEVATION))) (NTH 1 (CDR (ASSOC 10 (ENTGET ENTNAME))))))



  
  (SETQ REFERENCE_LIST (LIST (LIST MAST_NUMBER_X MAST_NUMBER_Y 0.0) (LIST TC_REFERENCE_X TC_REFERENCE_Y 0.0) (LIST SPAN_REFERENCE_X SPAN_REFERENCE_Y 0.0)))
  (SETQ REFERENCE_LIST1 (LIST (LIST FDN_REFERENCE_X FDN_REFERENCE_Y 0.0) (LIST RD_REFERENCE_X RD_REFERENCE_Y 0.0)))
  ;(SETQ BS_PT (CDR (ASSOC 10 (ENTGET ENTNAME))))

  (SETQ REFERENCE_LIST2 (LIST (LIST SD/EL_REFERENCE_X SD/EL_REFERENCE_Y 0.0) (LIST SB/ED_REFERENCE_X SB/ED_REFERENCE_Y 0.0) (LIST AB/AS/ASD_REFERENCE_X AB/AS/ASD_REFERENCE_Y 0.0) (LIST RADIUS/SUPER_ELEVATION_X RADIUS/SUPER_ELEVATION_Y 0.0)))
  
  (SETQ AS (GET_DYNAMIC_PROPERTIES ENTNAME '("SGM1 X" "IMM1 X" "SGM1 Y" "IMM1 Y" "LEAD-LENGTH" "LEAD-ANGLE" "D1" "D2")))


  (SETQ REFERENCE_LEAD_LENGTH (NTH 1 (NTH 0 (GET_DYNAMIC_PROPERTIES ENTNAME '("LEAD-LENGTH")))))
  (SETQ REFERENCE_IMPLANTATION (ATOF (NTH 0 (SINGLE_ELE_LIST (EXTRACT_ATTRIBUTES ENTNAME (LIST "IMPLANTATION1" ) 1) 1))))
  (SETQ BASE_ROTATION (VLAX-GET-PROPERTY (VLAX-ENAME->VLA-OBJECT ENTNAME) 'ROTATION))



  (SETQ VISIBILITY_SPAN (NTH 0 (SINGLE_ELE_LIST (EXTRACT_ATTRIBUTES ENTNAME (LIST "SPAN1" ) 3) 1)))
  (SETQ VISIBILITY_TC (NTH 0 (SINGLE_ELE_LIST (EXTRACT_ATTRIBUTES ENTNAME (LIST "TC1" ) 3) 1)))
  (SETQ VISIBILITY_FDN (NTH 0 (SINGLE_ELE_LIST (EXTRACT_ATTRIBUTES ENTNAME (LIST "FOUNDATION_TYPE1" ) 3) 1)))
  (SETQ VISIBILITY_RD (NTH 0 (SINGLE_ELE_LIST (EXTRACT_ATTRIBUTES ENTNAME (LIST "RD1" ) 3) 1)))

  (SETQ VISIBILITY_SD/EL (NTH 0 (SINGLE_ELE_LIST (EXTRACT_ATTRIBUTES ENTNAME (LIST "STEP_DISTANCE/EMBEDDED_LENGTH" ) 3) 1)))
  (SETQ VISIBILITY_SB/ED (NTH 0 (SINGLE_ELE_LIST (EXTRACT_ATTRIBUTES ENTNAME (LIST "SUPER_BLOCK/EXTRA_DEPTH" ) 3) 1)))
  (SETQ VISIBILITY_AB/AS/ASD (NTH 0 (SINGLE_ELE_LIST (EXTRACT_ATTRIBUTES ENTNAME (LIST "ANCHOR_BLOCK/ANCHOR_STEP/ANCHOR_SETTING_DISTANCE" ) 3) 1)))
  (SETQ VISIBILITY_RADIUS/SUPER_ELEVATION (NTH 0 (SINGLE_ELE_LIST (EXTRACT_ATTRIBUTES ENTNAME (LIST "RADIUS/SUPER_ELEVATION" ) 3) 1)))

  
(SETQ I 0 COLOUR_CODE NIL INSERTION_POINT NIL MAST_ROTATION NIL CENTER_POINT NIL TEMP_MAST_ENTITY NIL MAST_LIST NIL)
(SETQ FLAG "Y")
(SETQ MAST_LIST NIL)
(SETQ I 0)
(WHILE (< I (LENGTH SNAP_POINTS))
(SETQ TEMP_ELE (NTH 0 (NTH I SNAP_POINTS)))
(SETQ COLOUR_CODE (CDR (ASSOC 62  (ENTGET (NTH 0 (NTH I SNAP_POINTS))))))



(IF (/= (VL-POSITION COLOUR_CODE (LIST 3 8 9 7 4 6)) NIL)
(PROGN
(SETQ COLOUR_CODE (CDR (ASSOC 62  (ENTGET (NTH 0 (NTH I INSERTION_POINTS_SPAN))))))
(SETQ INSERTION_POINT (NTH 3 (NTH I INSERTION_POINTS_SPAN)))
(COMMAND "INSERT" "SINGLE_CANT_MAST" INSERTION_POINT "1" "0" )
(COMMAND "ROTATE" (ENTLAST) "" INSERTION_POINT "R" INSERTION_POINT (POLAR INSERTION_POINT (/ (* 3 PI) 2) 1) "P" (NTH 3 (NTH I INSERTION_POINTS_SPAN)) (NTH 1 (NTH I INSERTION_POINTS_SPAN)))
(IF (/= I (- (LENGTH SNAP_POINTS) 1)) (PROGN (MODIFY_ATTRIBUTES (ENTLAST) '("SPAN1") (LIST (NTH 2 (NTH I INSERTION_POINTS_SPAN))))))
(INSERT_DYNAMIC_PROPERTIES (ENTLAST) (SINGLE_ELE_LIST AS 0) (SINGLE_ELE_LIST AS 1))
(SETQ MAST_ROTATION (VLAX-GET-PROPERTY (VLAX-ENAME->VLA-OBJECT (ENTLAST)) 'ROTATION))
(SETQ CENTER_POINT (NTH 0 (TRANSFORM (BUILD_LIST (FILTER_LIST (LIST "CIRCLE") (BLOCK_ENAME1 (ENTLAST)) 1) (LIST 3 4 5)) INSERTION_POINT MAST_ROTATION)))
(SETQ TEMP_MAST_ENTITY (ENTLAST))


    (SETQ BASE_POINT (CDR (ASSOC 10 (ENTGET TEMP_MAST_ENTITY))))
    ;(SETQ ROTATION (VLAX-GET-PROPERTY (VLAX-ENAME->VLA-OBJECT TEMP_MAST_ENTITY) 'ROTATION))
    (SETQ TEMP_IMPLANTATION (ATOF (NTH 0 (SINGLE_ELE_LIST (EXTRACT_ATTRIBUTES TEMP_MAST_ENTITY (LIST "IMPLANTATION1" ) 1) 1))))
    (SETQ TEMP_POINT_LIST (TRANSFORM REFERENCE_LIST BASE_POINT (-  MAST_ROTATION BASE_ROTATION)))
    (SETQ TEMP_POINT_LIST1 (TRANSFORM_ADJ REFERENCE_LIST1 BASE_POINT (-  MAST_ROTATION BASE_ROTATION) (- REFERENCE_IMPLANTATION TEMP_IMPLANTATION)))
    (SETQ TEMP_POINT_LIST2 (TRANSFORM_ADJ REFERENCE_LIST2 BASE_POINT (-  MAST_ROTATION BASE_ROTATION) (- REFERENCE_IMPLANTATION TEMP_IMPLANTATION)))

    (INSERT_DYNAMIC_PROPERTIES TEMP_MAST_ENTITY (SINGLE_ELE_LIST AS 0) (SINGLE_ELE_LIST AS 1))
    (INSERT_DYNAMIC_PROPERTIES TEMP_MAST_ENTITY (LIST "LEAD-LENGTH") (LIST (- (+ REFERENCE_LEAD_LENGTH REFERENCE_IMPLANTATION) TEMP_IMPLANTATION)))
    
    (CHANGE_TEXT_ALIGNMENT_POINT TEMP_MAST_ENTITY '("MAST_NUMBER_LINK1") (LIST (NTH 0 TEMP_POINT_LIST)))
    (CHANGE_TEXT_ALIGNMENT_POINT TEMP_MAST_ENTITY '("TC1") (LIST (NTH 1 TEMP_POINT_LIST)))
    (CHANGE_TEXT_ALIGNMENT_POINT TEMP_MAST_ENTITY '("SPAN1") (LIST (NTH 2 TEMP_POINT_LIST)))
    
    (CHANGE_TEXT_ALIGNMENT_POINT TEMP_MAST_ENTITY '("FOUNDATION_TYPE1") (LIST (NTH 0 TEMP_POINT_LIST1)))
    (CHANGE_TEXT_ALIGNMENT_POINT TEMP_MAST_ENTITY '("RD1") (LIST (NTH 1 TEMP_POINT_LIST1)))

    (CHANGE_TEXT_ALIGNMENT_POINT TEMP_MAST_ENTITY '("STEP_DISTANCE/EMBEDDED_LENGTH" "SUPER_BLOCK/EXTRA_DEPTH" "ANCHOR_BLOCK/ANCHOR_STEP/ANCHOR_SETTING_DISTANCE" "RADIUS/SUPER_ELEVATION") TEMP_POINT_LIST2)

    
    (CHANGE_VISIBILITY TEMP_MAST_ENTITY (LIST "SPAN1" "TC1" "FOUNDATION_TYPE1" "RD1" ) (LIST (ITOA VISIBILITY_SPAN) (ITOA VISIBILITY_TC) (ITOA VISIBILITY_FDN) (ITOA VISIBILITY_RD) ))
    (CHANGE_VISIBILITY TEMP_MAST_ENTITY (LIST "STEP_DISTANCE/EMBEDDED_LENGTH" "SUPER_BLOCK/EXTRA_DEPTH" "ANCHOR_BLOCK/ANCHOR_STEP/ANCHOR_SETTING_DISTANCE" "RADIUS/SUPER_ELEVATION") (LIST (ITOA VISIBILITY_SD/EL) (ITOA VISIBILITY_SB/ED) (ITOA VISIBILITY_AB/AS/ASD) (ITOA VISIBILITY_RADIUS/SUPER_ELEVATION)))

    (SETQ MAST_LIST (CONS (LIST TEMP_MAST_ENTITY INSERTION_POINT (NTH 2 (NTH I INSERTION_POINTS_SPAN))) MAST_LIST))




(COMMAND "INSERT" "SUPER_MAST" CENTER_POINT "1" (* (/ 180 PI) MAST_ROTATION))
(CHANGE_FLIP (ENTLAST) "STF1")
(INSERT_ADDITIONAL_BLOCKS_GPS TEMP_MAST_ENTITY (NTH I SNAP_POINTS) "UP")
)
)


(IF (/= (VL-POSITION COLOUR_CODE (LIST 2 1 5)) NIL)
(PROGN
(SETQ INSERTION_POINT (NTH 3 (NTH I INSERTION_POINTS_SPAN)))
(COMMAND "INSERT" "DOUBLE_CANT_MAST" INSERTION_POINT "1" "0" )
(COMMAND "ROTATE" (ENTLAST) "" INSERTION_POINT "R" INSERTION_POINT (POLAR INSERTION_POINT (/ (* 3 PI) 2) 1) "P" (NTH 3 (NTH I INSERTION_POINTS_SPAN)) (NTH 1 (NTH I INSERTION_POINTS_SPAN)))
(IF (/= I (- (LENGTH SNAP_POINTS) 1)) (PROGN (MODIFY_ATTRIBUTES (ENTLAST) '("SPAN1" "SPAN2") (LIST (NTH 2 (NTH I INSERTION_POINTS_SPAN)) (NTH 2 (NTH I INSERTION_POINTS_SPAN))))))
;(INSERT_DYNAMIC_PROPERTIES (ENTLAST) (SINGLE_ELE_LIST AS 0) (SINGLE_ELE_LIST AS 1))
(SETQ MAST_ROTATION (VLAX-GET-PROPERTY (VLAX-ENAME->VLA-OBJECT (ENTLAST)) 'ROTATION))
(SETQ CENTER_POINT (NTH 0 (TRANSFORM (BUILD_LIST (FILTER_LIST (LIST "CIRCLE") (BLOCK_ENAME1 (ENTLAST)) 1) (LIST 3 4 5)) INSERTION_POINT MAST_ROTATION)))
(SETQ TEMP_MAST_ENTITY (ENTLAST))




    (SETQ BASE_POINT (CDR (ASSOC 10 (ENTGET TEMP_MAST_ENTITY))))
    ;(SETQ ROTATION (VLAX-GET-PROPERTY (VLAX-ENAME->VLA-OBJECT TEMP_MAST_ENTITY) 'ROTATION))
    (SETQ TEMP_IMPLANTATION (ATOF (NTH 0 (SINGLE_ELE_LIST (EXTRACT_ATTRIBUTES TEMP_MAST_ENTITY (LIST "IMPLANTATION1" ) 1) 1))))
    (SETQ TEMP_POINT_LIST (TRANSFORM REFERENCE_LIST BASE_POINT (-  MAST_ROTATION BASE_ROTATION)))
    (SETQ TEMP_POINT_LIST1 (TRANSFORM_ADJ REFERENCE_LIST1 BASE_POINT (-  MAST_ROTATION BASE_ROTATION) (- REFERENCE_IMPLANTATION TEMP_IMPLANTATION)))
    (SETQ TEMP_POINT_LIST2 (TRANSFORM_ADJ REFERENCE_LIST2 BASE_POINT (-  MAST_ROTATION BASE_ROTATION) (- REFERENCE_IMPLANTATION TEMP_IMPLANTATION)))

    (INSERT_DYNAMIC_PROPERTIES TEMP_MAST_ENTITY (SINGLE_ELE_LIST AS 0) (SINGLE_ELE_LIST AS 1))
    (INSERT_DYNAMIC_PROPERTIES TEMP_MAST_ENTITY (LIST "LEAD-LENGTH") (LIST (- (+ REFERENCE_LEAD_LENGTH REFERENCE_IMPLANTATION) TEMP_IMPLANTATION)))
    
    (CHANGE_TEXT_ALIGNMENT_POINT TEMP_MAST_ENTITY '("MAST_NUMBER_LINK1") (LIST (NTH 0 TEMP_POINT_LIST)))
    (CHANGE_TEXT_ALIGNMENT_POINT TEMP_MAST_ENTITY '("TC1") (LIST (NTH 1 TEMP_POINT_LIST)))
    (CHANGE_TEXT_ALIGNMENT_POINT TEMP_MAST_ENTITY '("SPAN1") (LIST (NTH 2 TEMP_POINT_LIST)))
    
    (CHANGE_TEXT_ALIGNMENT_POINT TEMP_MAST_ENTITY '("FOUNDATION_TYPE1") (LIST (NTH 0 TEMP_POINT_LIST1)))
    (CHANGE_TEXT_ALIGNMENT_POINT TEMP_MAST_ENTITY '("RD1") (LIST (NTH 1 TEMP_POINT_LIST1)))

    (CHANGE_TEXT_ALIGNMENT_POINT TEMP_MAST_ENTITY '("STEP_DISTANCE/EMBEDDED_LENGTH" "SUPER_BLOCK/EXTRA_DEPTH" "ANCHOR_BLOCK/ANCHOR_STEP/ANCHOR_SETTING_DISTANCE" "RADIUS/SUPER_ELEVATION") TEMP_POINT_LIST2)

    (CHANGE_VISIBILITY TEMP_MAST_ENTITY (LIST "SPAN1" "TC1" "FOUNDATION_TYPE1" "RD1" ) (LIST (ITOA VISIBILITY_SPAN) (ITOA VISIBILITY_TC) (ITOA VISIBILITY_FDN) (ITOA VISIBILITY_RD) ))
    (CHANGE_VISIBILITY TEMP_MAST_ENTITY (LIST "STEP_DISTANCE/EMBEDDED_LENGTH" "SUPER_BLOCK/EXTRA_DEPTH" "ANCHOR_BLOCK/ANCHOR_STEP/ANCHOR_SETTING_DISTANCE" "RADIUS/SUPER_ELEVATION") (LIST (ITOA VISIBILITY_SD/EL) (ITOA VISIBILITY_SB/ED) (ITOA VISIBILITY_AB/AS/ASD) (ITOA VISIBILITY_RADIUS/SUPER_ELEVATION)))
    (SETQ MAST_LIST (CONS (LIST TEMP_MAST_ENTITY INSERTION_POINT (NTH 2 (NTH I INSERTION_POINTS_SPAN))) MAST_LIST))



(COMMAND "INSERT" "SUPER_MAST" CENTER_POINT "1" (* (/ 180 PI) MAST_ROTATION))
(CHANGE_FLIP (ENTLAST) "STF1")

(INSERT_ADDITIONAL_BLOCKS_GPS TEMP_MAST_ENTITY (NTH I SNAP_POINTS) "UP")
  ))

(SETQ I (+ I 1))
)
(REVERSE MAST_LIST)
)





(DEFUN INSERT_MASTS_DN_NORMAL_GPS ( OFFSET_ENTITIES1 STARTING_OFFSET TRACK_ENTITY SCALE ENTNAME / ENTNAME  I TEMP_ELE INSERTION_POINT MAST_LENGTH VALUES POINT POINT1 IMP_REFERENCE SG_REFERENCE FLAG MAST_LIST IMP_POINT STAG_POINT SPAN_REFERENCE SCALE)
(SETQ OS_MODE (GETVAR "OSMODE"))
(SETQ 3DOS_MODE (GETVAR "3DOSMODE"))
(SETVAR "OSMODE" 0)
(SETVAR "3DOSMODE" 0)
(COMMAND "UCS" "W")
(SETQ SNAP_POINTS (SORT_ENTITIES_ALONG_CURVE (NTH 0 TRACK_ENTITY) (GET_OFFSET_INTERSECTION_POINTS OFFSET_ENTITIES1 (NTH 0 TRACK_ENTITY)) (ASSOC STARTING_OFFSET (GET_OFFSET_INTERSECTION_POINTS OFFSET_ENTITIES1 (NTH 0 TRACK_ENTITY))) 1 1))
(SETQ SNAP_POINTS (INDENTIFY_LOCATIONS_GPS SNAP_POINTS "UP"))
(SETQ SNAP_POINTS_SPAN (SPAN_FROM_OFFSETS (NTH 0 TRACK_ENTITY) (BUILD_LIST SNAP_POINTS (LIST 0 1)) 1))
(SETQ INSERTION_POINTS_SPAN (GET_MAST_INSERTION_POINT_GPS_RIGHT (NTH 0 TRACK_ENTITY) SNAP_POINTS_SPAN (N_ELE_LIST 3.00 (LENGTH SNAP_POINTS_SPAN)) 1))
(SETQ MAST_LENGTH (GET_DYNAMIC_PROPERTIES ENTNAME '("STL1")))



  
(SETQ MAST_NUMBER (GET_TEXT_ALIGNMENT_POINT (LIST ENTNAME) "MAST_NUMBER_LINK1" 0))
  (SETQ MAST_NUMBER_X (- (NTH 0 (NTH 1 (NTH 0 MAST_NUMBER))) (NTH 0 (CDR (ASSOC 10 (ENTGET ENTNAME))))))
  (SETQ MAST_NUMBER_Y (- (NTH 1 (NTH 1 (NTH 0 MAST_NUMBER))) (NTH 1 (CDR (ASSOC 10 (ENTGET ENTNAME))))))
  
  (SETQ TC_REFERENCE (GET_TEXT_ALIGNMENT_POINT (LIST ENTNAME) "TC1" 0))
  (SETQ TC_REFERENCE_X (- (NTH 0 (NTH 1 (NTH 0 TC_REFERENCE))) (NTH 0 (CDR (ASSOC 10 (ENTGET ENTNAME))))))
  (SETQ TC_REFERENCE_Y (- (NTH 1 (NTH 1 (NTH 0 TC_REFERENCE))) (NTH 1 (CDR (ASSOC 10 (ENTGET ENTNAME))))))
  
  (SETQ SPAN_REFERENCE (GET_TEXT_ALIGNMENT_POINT (LIST ENTNAME) "SPAN1" 0))
  (SETQ SPAN_REFERENCE_X (- (NTH 0 (NTH 1 (NTH 0 SPAN_REFERENCE))) (NTH 0 (CDR (ASSOC 10 (ENTGET ENTNAME))))))
  (SETQ SPAN_REFERENCE_Y (- (NTH 1 (NTH 1 (NTH 0 SPAN_REFERENCE))) (NTH 1 (CDR (ASSOC 10 (ENTGET ENTNAME))))))
  
  
  (SETQ FDN_REFERENCE (GET_TEXT_ALIGNMENT_POINT (LIST ENTNAME) "FOUNDATION_TYPE1" 0))
  (SETQ FDN_REFERENCE_X (- (NTH 0 (NTH 1 (NTH 0 FDN_REFERENCE))) (NTH 0 (CDR (ASSOC 10 (ENTGET ENTNAME))))))
  (SETQ FDN_REFERENCE_Y (- (NTH 1 (NTH 1 (NTH 0 FDN_REFERENCE))) (NTH 1 (CDR (ASSOC 10 (ENTGET ENTNAME))))))
  
  (SETQ RD_REFERENCE (GET_TEXT_ALIGNMENT_POINT (LIST ENTNAME) "RD1" 0))
  (SETQ RD_REFERENCE_X (- (NTH 0 (NTH 1 (NTH 0 RD_REFERENCE))) (NTH 0 (CDR (ASSOC 10 (ENTGET ENTNAME))))))
  (SETQ RD_REFERENCE_Y (- (NTH 1 (NTH 1 (NTH 0 RD_REFERENCE))) (NTH 1 (CDR (ASSOC 10 (ENTGET ENTNAME))))))
  
  (SETQ SD/EL_REFERENCE (GET_TEXT_ALIGNMENT_POINT (LIST ENTNAME) "STEP_DISTANCE/EMBEDDED_LENGTH" 0))
  (SETQ SD/EL_REFERENCE_X (- (NTH 0 (NTH 1 (NTH 0 SD/EL_REFERENCE))) (NTH 0 (CDR (ASSOC 10 (ENTGET ENTNAME))))))
  (SETQ SD/EL_REFERENCE_Y (- (NTH 1 (NTH 1 (NTH 0 SD/EL_REFERENCE))) (NTH 1 (CDR (ASSOC 10 (ENTGET ENTNAME))))))

  (SETQ SB/ED_REFERENCE (GET_TEXT_ALIGNMENT_POINT (LIST ENTNAME) "SUPER_BLOCK/EXTRA_DEPTH" 0))
  (SETQ SB/ED_REFERENCE_X (- (NTH 0 (NTH 1 (NTH 0 SB/ED_REFERENCE))) (NTH 0 (CDR (ASSOC 10 (ENTGET ENTNAME))))))
  (SETQ SB/ED_REFERENCE_Y (- (NTH 1 (NTH 1 (NTH 0 SB/ED_REFERENCE))) (NTH 1 (CDR (ASSOC 10 (ENTGET ENTNAME))))))

  (SETQ AB/AS/ASD_REFERENCE (GET_TEXT_ALIGNMENT_POINT (LIST ENTNAME) "ANCHOR_BLOCK/ANCHOR_STEP/ANCHOR_SETTING_DISTANCE" 0))
  (SETQ AB/AS/ASD_REFERENCE_X (- (NTH 0 (NTH 1 (NTH 0 AB/AS/ASD_REFERENCE))) (NTH 0 (CDR (ASSOC 10 (ENTGET ENTNAME))))))
  (SETQ AB/AS/ASD_REFERENCE_Y (- (NTH 1 (NTH 1 (NTH 0 AB/AS/ASD_REFERENCE))) (NTH 1 (CDR (ASSOC 10 (ENTGET ENTNAME))))))

  (SETQ RADIUS/SUPER_ELEVATION (GET_TEXT_ALIGNMENT_POINT (LIST ENTNAME) "RADIUS/SUPER_ELEVATION" 0))
  (SETQ RADIUS/SUPER_ELEVATION_X (- (NTH 0 (NTH 1 (NTH 0 RADIUS/SUPER_ELEVATION))) (NTH 0 (CDR (ASSOC 10 (ENTGET ENTNAME))))))
  (SETQ RADIUS/SUPER_ELEVATION_Y (- (NTH 1 (NTH 1 (NTH 0 RADIUS/SUPER_ELEVATION))) (NTH 1 (CDR (ASSOC 10 (ENTGET ENTNAME))))))
  
  (SETQ REFERENCE_LIST (LIST (LIST MAST_NUMBER_X MAST_NUMBER_Y 0.0) (LIST TC_REFERENCE_X TC_REFERENCE_Y 0.0) (LIST SPAN_REFERENCE_X SPAN_REFERENCE_Y 0.0)))
  (SETQ REFERENCE_LIST1 (LIST (LIST FDN_REFERENCE_X FDN_REFERENCE_Y 0.0) (LIST RD_REFERENCE_X RD_REFERENCE_Y 0.0) ))
  ;(SETQ BS_PT (CDR (ASSOC 10 (ENTGET ENTNAME))))
  
  (SETQ REFERENCE_LIST2 (LIST (LIST SD/EL_REFERENCE_X SD/EL_REFERENCE_Y 0.0) (LIST SB/ED_REFERENCE_X SB/ED_REFERENCE_Y 0.0) (LIST AB/AS/ASD_REFERENCE_X AB/AS/ASD_REFERENCE_Y 0.0) (LIST RADIUS/SUPER_ELEVATION_X RADIUS/SUPER_ELEVATION_Y 0.0)))
  
  (SETQ AS (GET_DYNAMIC_PROPERTIES ENTNAME '("SGM1 X" "IMM1 X" "SGM1 Y" "IMM1 Y" "LEAD-LENGTH" "LEAD-ANGLE" "D1" "D2")))


  (SETQ REFERENCE_LEAD_LENGTH (NTH 1 (NTH 0 (GET_DYNAMIC_PROPERTIES ENTNAME '("LEAD-LENGTH")))))
  (SETQ REFERENCE_IMPLANTATION (ATOF (NTH 0 (SINGLE_ELE_LIST (EXTRACT_ATTRIBUTES ENTNAME (LIST "IMPLANTATION1" ) 1) 1))))
  (SETQ BASE_ROTATION (VLAX-GET-PROPERTY (VLAX-ENAME->VLA-OBJECT ENTNAME) 'ROTATION))



  (SETQ VISIBILITY_SPAN (NTH 0 (SINGLE_ELE_LIST (EXTRACT_ATTRIBUTES ENTNAME (LIST "SPAN1" ) 3) 1)))
  (SETQ VISIBILITY_TC (NTH 0 (SINGLE_ELE_LIST (EXTRACT_ATTRIBUTES ENTNAME (LIST "TC1" ) 3) 1)))
  (SETQ VISIBILITY_FDN (NTH 0 (SINGLE_ELE_LIST (EXTRACT_ATTRIBUTES ENTNAME (LIST "FOUNDATION_TYPE1" ) 3) 1)))
  (SETQ VISIBILITY_RD (NTH 0 (SINGLE_ELE_LIST (EXTRACT_ATTRIBUTES ENTNAME (LIST "RD1" ) 3) 1)))


  (SETQ VISIBILITY_SD/EL (NTH 0 (SINGLE_ELE_LIST (EXTRACT_ATTRIBUTES ENTNAME (LIST "STEP_DISTANCE/EMBEDDED_LENGTH" ) 3) 1)))
  (SETQ VISIBILITY_SB/ED (NTH 0 (SINGLE_ELE_LIST (EXTRACT_ATTRIBUTES ENTNAME (LIST "SUPER_BLOCK/EXTRA_DEPTH" ) 3) 1)))
  (SETQ VISIBILITY_AB/AS/ASD (NTH 0 (SINGLE_ELE_LIST (EXTRACT_ATTRIBUTES ENTNAME (LIST "ANCHOR_BLOCK/ANCHOR_STEP/ANCHOR_SETTING_DISTANCE" ) 3) 1)))
  (SETQ VISIBILITY_RADIUS/SUPER_ELEVATION (NTH 0 (SINGLE_ELE_LIST (EXTRACT_ATTRIBUTES ENTNAME (LIST "RADIUS/SUPER_ELEVATION" ) 3) 1)))


  
(SETQ I 0 COLOUR_CODE NIL INSERTION_POINT NIL MAST_ROTATION NIL CENTER_POINT NIL TEMP_MAST_ENTITY NIL MAST_LIST NIL)
(SETQ FLAG "Y")
(SETQ MAST_LIST NIL)
(SETQ I 0)
(WHILE (< I (LENGTH SNAP_POINTS))
(SETQ TEMP_ELE (NTH 0 (NTH I SNAP_POINTS)))
(SETQ COLOUR_CODE (CDR (ASSOC 62  (ENTGET (NTH 0 (NTH I INSERTION_POINTS_SPAN))))))



(IF (/= (VL-POSITION COLOUR_CODE (LIST 3 8 9 7 4 6)) NIL)
(PROGN
(SETQ COLOUR_CODE (CDR (ASSOC 62  (ENTGET (NTH 0 (NTH I INSERTION_POINTS_SPAN))))))

(SETQ INSERTION_POINT (NTH 3 (NTH I INSERTION_POINTS_SPAN)))
(COMMAND "INSERT" "SINGLE_CANT_MAST" INSERTION_POINT "1" "0" )
(CHANGE_FLIP (ENTLAST) "STF1")
(COMMAND "ROTATE" (ENTLAST) "" INSERTION_POINT "R" INSERTION_POINT (POLAR INSERTION_POINT (/ PI 2) 1) "P" (NTH 3 (NTH I INSERTION_POINTS_SPAN)) (NTH 1 (NTH I INSERTION_POINTS_SPAN)))
(IF (/= I (- (LENGTH SNAP_POINTS) 1)) (PROGN (MODIFY_ATTRIBUTES (ENTLAST) '("SPAN1") (LIST (NTH 2 (NTH I INSERTION_POINTS_SPAN))))))
(INSERT_DYNAMIC_PROPERTIES (ENTLAST) (SINGLE_ELE_LIST AS 0) (SINGLE_ELE_LIST AS 1))
(SETQ MAST_ROTATION (VLAX-GET-PROPERTY (VLAX-ENAME->VLA-OBJECT (ENTLAST)) 'ROTATION))
(SETQ CENTER_POINT (NTH 0 (TRANSFORM (BUILD_LIST (FILTER_LIST (LIST "CIRCLE") (BLOCK_ENAME1 (ENTLAST)) 1) (LIST 3 4 5)) INSERTION_POINT MAST_ROTATION)))



    (SETQ TEMP_MAST_ENTITY (ENTLAST))
    (SETQ BASE_POINT (CDR (ASSOC 10 (ENTGET TEMP_MAST_ENTITY))))
    ;(SETQ ROTATION (VLAX-GET-PROPERTY (VLAX-ENAME->VLA-OBJECT TEMP_MAST_ENTITY) 'ROTATION))
    (SETQ TEMP_IMPLANTATION (ATOF (NTH 0 (SINGLE_ELE_LIST (EXTRACT_ATTRIBUTES TEMP_MAST_ENTITY (LIST "IMPLANTATION1" ) 1) 1))))
    (SETQ TEMP_POINT_LIST (TRANSFORM REFERENCE_LIST BASE_POINT (-  MAST_ROTATION BASE_ROTATION)))
    (SETQ TEMP_POINT_LIST1 (TRANSFORM_ADJ REFERENCE_LIST1 BASE_POINT (-  MAST_ROTATION BASE_ROTATION) (- REFERENCE_IMPLANTATION TEMP_IMPLANTATION)))
    (SETQ TEMP_POINT_LIST2 (TRANSFORM_ADJ REFERENCE_LIST2 BASE_POINT (-  MAST_ROTATION BASE_ROTATION) (- REFERENCE_IMPLANTATION TEMP_IMPLANTATION)))

    (INSERT_DYNAMIC_PROPERTIES TEMP_MAST_ENTITY (SINGLE_ELE_LIST AS 0) (SINGLE_ELE_LIST AS 1))
    (INSERT_DYNAMIC_PROPERTIES TEMP_MAST_ENTITY (LIST "LEAD-LENGTH") (LIST (- (+ REFERENCE_LEAD_LENGTH REFERENCE_IMPLANTATION) TEMP_IMPLANTATION)))
    
    (CHANGE_TEXT_ALIGNMENT_POINT TEMP_MAST_ENTITY '("MAST_NUMBER_LINK1") (LIST (NTH 0 TEMP_POINT_LIST)))
    (CHANGE_TEXT_ALIGNMENT_POINT TEMP_MAST_ENTITY '("TC1") (LIST (NTH 1 TEMP_POINT_LIST)))
    (CHANGE_TEXT_ALIGNMENT_POINT TEMP_MAST_ENTITY '("SPAN1") (LIST (NTH 2 TEMP_POINT_LIST)))
    
    (CHANGE_TEXT_ALIGNMENT_POINT TEMP_MAST_ENTITY '("FOUNDATION_TYPE1") (LIST (NTH 0 TEMP_POINT_LIST1)))
    (CHANGE_TEXT_ALIGNMENT_POINT TEMP_MAST_ENTITY '("RD1") (LIST (NTH 1 TEMP_POINT_LIST1)))
    (CHANGE_TEXT_ALIGNMENT_POINT TEMP_MAST_ENTITY '("STEP_DISTANCE/EMBEDDED_LENGTH" "SUPER_BLOCK/EXTRA_DEPTH" "ANCHOR_BLOCK/ANCHOR_STEP/ANCHOR_SETTING_DISTANCE" "RADIUS/SUPER_ELEVATION") TEMP_POINT_LIST2)
    
    (CHANGE_VISIBILITY TEMP_MAST_ENTITY (LIST "SPAN1" "TC1" "FOUNDATION_TYPE1" "RD1" ) (LIST (ITOA VISIBILITY_SPAN) (ITOA VISIBILITY_TC) (ITOA VISIBILITY_FDN) (ITOA VISIBILITY_RD) ))
    (CHANGE_VISIBILITY TEMP_MAST_ENTITY (LIST "STEP_DISTANCE/EMBEDDED_LENGTH" "SUPER_BLOCK/EXTRA_DEPTH" "ANCHOR_BLOCK/ANCHOR_STEP/ANCHOR_SETTING_DISTANCE" "RADIUS/SUPER_ELEVATION") (LIST (ITOA VISIBILITY_SD/EL) (ITOA VISIBILITY_SB/ED) (ITOA VISIBILITY_AB/AS/ASD) (ITOA VISIBILITY_RADIUS/SUPER_ELEVATION)))
    (SETQ MAST_LIST (CONS (LIST TEMP_MAST_ENTITY INSERTION_POINT (NTH 2 (NTH I INSERTION_POINTS_SPAN))) MAST_LIST))


(COMMAND "INSERT" "SUPER_MAST" CENTER_POINT "1" (* (/ 180 PI) MAST_ROTATION))

(INSERT_ADDITIONAL_BLOCKS_GPS TEMP_MAST_ENTITY (NTH I SNAP_POINTS) "DN")
))



(IF (/= (VL-POSITION COLOUR_CODE (LIST 2 1 5)) NIL)
(PROGN
(SETQ INSERTION_POINT (NTH 3 (NTH I INSERTION_POINTS_SPAN)))
(COMMAND "INSERT" "DOUBLE_CANT_MAST" INSERTION_POINT "1" "0" )
(CHANGE_FLIP (ENTLAST) "STF1")
(COMMAND "ROTATE" (ENTLAST) "" INSERTION_POINT "R" INSERTION_POINT (POLAR INSERTION_POINT (/ PI 2) 1) "P" (NTH 3 (NTH I INSERTION_POINTS_SPAN)) (NTH 1 (NTH I INSERTION_POINTS_SPAN)))
(IF (/= I (- (LENGTH SNAP_POINTS) 1)) (PROGN (MODIFY_ATTRIBUTES (ENTLAST) '("SPAN1" "SPAN2") (LIST (NTH 2 (NTH I INSERTION_POINTS_SPAN)) (NTH 2 (NTH I INSERTION_POINTS_SPAN))))))
(INSERT_DYNAMIC_PROPERTIES (ENTLAST) (SINGLE_ELE_LIST AS 0) (SINGLE_ELE_LIST AS 1))
(SETQ MAST_ROTATION (VLAX-GET-PROPERTY (VLAX-ENAME->VLA-OBJECT (ENTLAST)) 'ROTATION))
(SETQ CENTER_POINT (NTH 0 (TRANSFORM (BUILD_LIST (FILTER_LIST (LIST "CIRCLE") (BLOCK_ENAME1 (ENTLAST)) 1) (LIST 3 4 5)) INSERTION_POINT MAST_ROTATION)))



    (SETQ TEMP_MAST_ENTITY (ENTLAST))
    (SETQ BASE_POINT (CDR (ASSOC 10 (ENTGET TEMP_MAST_ENTITY))))
    ;(SETQ ROTATION (VLAX-GET-PROPERTY (VLAX-ENAME->VLA-OBJECT TEMP_MAST_ENTITY) 'ROTATION))
    (SETQ TEMP_IMPLANTATION (ATOF (NTH 0 (SINGLE_ELE_LIST (EXTRACT_ATTRIBUTES TEMP_MAST_ENTITY (LIST "IMPLANTATION1" ) 1) 1))))
    (SETQ TEMP_POINT_LIST (TRANSFORM REFERENCE_LIST BASE_POINT (-  MAST_ROTATION BASE_ROTATION)))
    (SETQ TEMP_POINT_LIST1 (TRANSFORM_ADJ REFERENCE_LIST1 BASE_POINT (-  MAST_ROTATION BASE_ROTATION) (- REFERENCE_IMPLANTATION TEMP_IMPLANTATION)))
    (SETQ TEMP_POINT_LIST2 (TRANSFORM_ADJ REFERENCE_LIST2 BASE_POINT (-  MAST_ROTATION BASE_ROTATION) (- REFERENCE_IMPLANTATION TEMP_IMPLANTATION)))

    (INSERT_DYNAMIC_PROPERTIES TEMP_MAST_ENTITY (SINGLE_ELE_LIST AS 0) (SINGLE_ELE_LIST AS 1))
    (INSERT_DYNAMIC_PROPERTIES TEMP_MAST_ENTITY (LIST "LEAD-LENGTH") (LIST (- (+ REFERENCE_LEAD_LENGTH REFERENCE_IMPLANTATION) TEMP_IMPLANTATION)))
    
    (CHANGE_TEXT_ALIGNMENT_POINT TEMP_MAST_ENTITY '("MAST_NUMBER_LINK1") (LIST (NTH 0 TEMP_POINT_LIST)))
    (CHANGE_TEXT_ALIGNMENT_POINT TEMP_MAST_ENTITY '("TC1") (LIST (NTH 1 TEMP_POINT_LIST)))
    (CHANGE_TEXT_ALIGNMENT_POINT TEMP_MAST_ENTITY '("SPAN1") (LIST (NTH 2 TEMP_POINT_LIST)))
    
    (CHANGE_TEXT_ALIGNMENT_POINT TEMP_MAST_ENTITY '("FOUNDATION_TYPE1") (LIST (NTH 0 TEMP_POINT_LIST1)))
    (CHANGE_TEXT_ALIGNMENT_POINT TEMP_MAST_ENTITY '("RD1") (LIST (NTH 1 TEMP_POINT_LIST1)))
    (CHANGE_TEXT_ALIGNMENT_POINT TEMP_MAST_ENTITY '("STEP_DISTANCE/EMBEDDED_LENGTH" "SUPER_BLOCK/EXTRA_DEPTH" "ANCHOR_BLOCK/ANCHOR_STEP/ANCHOR_SETTING_DISTANCE" "RADIUS/SUPER_ELEVATION") TEMP_POINT_LIST2)
      
    (CHANGE_VISIBILITY TEMP_MAST_ENTITY (LIST "SPAN1" "TC1" "FOUNDATION_TYPE1" "RD1" ) (LIST (ITOA VISIBILITY_SPAN) (ITOA VISIBILITY_TC) (ITOA VISIBILITY_FDN) (ITOA VISIBILITY_RD) ))
    (CHANGE_VISIBILITY TEMP_MAST_ENTITY (LIST "STEP_DISTANCE/EMBEDDED_LENGTH" "SUPER_BLOCK/EXTRA_DEPTH" "ANCHOR_BLOCK/ANCHOR_STEP/ANCHOR_SETTING_DISTANCE" "RADIUS/SUPER_ELEVATION") (LIST (ITOA VISIBILITY_SD/EL) (ITOA VISIBILITY_SB/ED) (ITOA VISIBILITY_AB/AS/ASD) (ITOA VISIBILITY_RADIUS/SUPER_ELEVATION)))
    (SETQ MAST_LIST (CONS (LIST TEMP_MAST_ENTITY INSERTION_POINT (NTH 2 (NTH I INSERTION_POINTS_SPAN))) MAST_LIST))


(COMMAND "INSERT" "SUPER_MAST" CENTER_POINT "1" (* (/ 180 PI) MAST_ROTATION))
(INSERT_ADDITIONAL_BLOCKS_GPS TEMP_MAST_ENTITY (NTH I SNAP_POINTS) "DN")
  ))

(SETQ I (+ I 1))
)
(REVERSE MAST_LIST)
)






(DEFUN INSERT_ADDITIONAL_BLOCKS_GPS ( MAST_ENTNAME INFO TRACK_TYPE / INDENTIFICATION_STRING WIRE_NUMBER1 WIRE_NUMBER2  )
  (SETQ MAIN_BLOCK_INSERTION_POINT (CDR (ASSOC 10 (ENTGET MAST_ENTNAME))))
  (SETQ MAST_ROTATION (VLAX-GET-PROPERTY (VLAX-ENAME->VLA-OBJECT MAST_ENTNAME) 'ROTATION))
  (SETQ MAST_ROTATION1 (* (/ 180 PI) (VLAX-GET-PROPERTY (VLAX-ENAME->VLA-OBJECT MAST_ENTNAME) 'ROTATION)))
  (SETQ INDENTIFICATION_STRING (NTH 2 INFO))
  (SETQ WIRE_NUMBER1 (NTH 3 INFO))
  (SETQ WIRE_NUMBER2 (NTH 4 INFO))
  (SETQ NA 0)
  (IF (= TRACK_TYPE "UP")
  (PROGN
  (IF (= INDENTIFICATION_STRING "BWA_END")
    (PROGN
      (COMMAND "INSERT" "ANCHOR" (POLAR MAIN_BLOCK_INSERTION_POINT (+ (* 1 (/ PI 2)) MAST_ROTATION) 0.8) "1" MAST_ROTATION1)
      (INSERT_DYNAMIC_PROPERTIES (ENTLAST) '("LENGTHEN") (LIST 3.00))
      (CHANGE_FLIP (ENTLAST) "ANF1")
      (INSERT_ATTRIBUTES (ENTLAST) '("WIRE_RUN1") (LIST (LIST (+ (CAR MAIN_BLOCK_INSERTION_POINT) 11.40)  (- (CADR MAIN_BLOCK_INSERTION_POINT) 4.35) 0.0)))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (COMMAND "INSERT" "TENSION_LENGTH" (POLAR MAIN_BLOCK_INSERTION_POINT (+ (* 1 (/ PI 2)) MAST_ROTATION) 35) "1" MAST_ROTATION1)
      (COMMAND "INSERT" "JUMPER" (POLAR MAIN_BLOCK_INSERTION_POINT (+ 3.37217 MAST_ROTATION) 9.6994) "1" 0)
      (INSERT_DYNAMIC_PROPERTIES (ENTLAST) (LIST "ANR1") (LIST (+ MAST_ROTATION (* (/ PI 180) 228))))
      (INSERT_DYNAMIC_PROPERTIES (ENTLAST) '("Visibility1") (LIST "ATJ"))
      (MODIFY_ATTRIBUTES (ENTLAST) (LIST "JUMPER_TYPE2") (LIST "3ATJ"))
    )
  )

  (IF (= INDENTIFICATION_STRING "BWA_START")
    (PROGN
      (COMMAND "INSERT" "ANCHOR" (POLAR MAIN_BLOCK_INSERTION_POINT (+ (* 1 (/ PI 2)) MAST_ROTATION) 0.8) "1" MAST_ROTATION1)
      (INSERT_DYNAMIC_PROPERTIES (ENTLAST) '("LENGTHEN") (LIST 3.00))
      
      (INSERT_ATTRIBUTES (ENTLAST) '("WIRE_RUN1") (LIST (LIST (- (CAR MAIN_BLOCK_INSERTION_POINT) 16.00)  (- (CADR MAIN_BLOCK_INSERTION_POINT) 5.75) 0.0)))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (COMMAND "INSERT" "TENSION_LENGTH" (POLAR MAIN_BLOCK_INSERTION_POINT (+ (* 1 (/ PI 2)) MAST_ROTATION) 35) "1" MAST_ROTATION1)
      (CHANGE_FLIP (ENTLAST) "TLF2")
      ;(INSERT_DYNAMIC_PROPERTIES (ENTLAST) '("TLM4 X") (LIST (+ (NTH 1 (NTH 0 (GET_DYNAMIC_PROPERTIES (ENTLAST) '("TLM4 X")))) 24.00)))
      (COMMAND "INSERT" "JUMPER" (POLAR MAIN_BLOCK_INSERTION_POINT (+ 6.12985 MAST_ROTATION) 9.6994) "1" 0)
      (INSERT_DYNAMIC_PROPERTIES (ENTLAST) (LIST "ANR1") (LIST (+ MAST_ROTATION (* (/ PI 180) 228))))
      (INSERT_DYNAMIC_PROPERTIES (ENTLAST) '("Visibility1") (LIST "ATJ"))
      (MODIFY_ATTRIBUTES (ENTLAST) (LIST "JUMPER_TYPE2") (LIST "3ATJ"))
    )
  )


  (IF (= INDENTIFICATION_STRING "ACA_END")
    (PROGN
      (COMMAND "INSERT" "ANCHOR" (POLAR MAIN_BLOCK_INSERTION_POINT (+ (* 1 (/ PI 2)) MAST_ROTATION) 0.8) "1" MAST_ROTATION1)
      (CHANGE_FLIP (ENTLAST) "ANF1")
      (MODIFY_ATTRIBUTES (ENTLAST) (LIST "ANCHOR_TYPE1") (LIST "ACA"))
      (INSERT_ATTRIBUTES (ENTLAST) '("WIRE_RUN1") (LIST (LIST (+ (CAR MAIN_BLOCK_INSERTION_POINT) 11.40)  (- (CADR MAIN_BLOCK_INSERTION_POINT) 4.35) 0.0)))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (INSERT_DYNAMIC_PROPERTIES (ENTLAST) '("LENGTHEN" "Visibility1") (LIST 3.00 "WITHOUT WEIGHTS"))
    )
  )


  (IF (= INDENTIFICATION_STRING "ACA_START")
    (PROGN
      (COMMAND "INSERT" "ANCHOR" (POLAR MAIN_BLOCK_INSERTION_POINT (+ (* 1 (/ PI 2)) MAST_ROTATION) 0.8) "1" MAST_ROTATION1)
      (INSERT_DYNAMIC_PROPERTIES (ENTLAST) '("LENGTHEN") (LIST 3.00))
      
      (MODIFY_ATTRIBUTES (ENTLAST) (LIST "ANCHOR_TYPE1") (LIST "ACA"))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (INSERT_DYNAMIC_PROPERTIES (ENTLAST) '("LENGTHEN" "Visibility1") (LIST 3.00 "WITHOUT WEIGHTS"))
      (INSERT_ATTRIBUTES (ENTLAST) '("WIRE_RUN1") (LIST (LIST (- (CAR MAIN_BLOCK_INSERTION_POINT) 16.00)  (- (CADR MAIN_BLOCK_INSERTION_POINT) 5.75) 0.0)))
    )
  )



  (IF (= INDENTIFICATION_STRING "OLC")
    (PROGN
      (COMMAND "INSERT" "OLC" (POLAR MAIN_BLOCK_INSERTION_POINT (+ (* 1 (/ PI 2)) MAST_ROTATION) 45) "1" MAST_ROTATION1)
      (MODIFY_ATTRIBUTES (ENTLAST) (LIST "TRACK") (LIST "FOR DN MAIN"))
      (COMMAND "INSERT" "JUMPER" (POLAR MAIN_BLOCK_INSERTION_POINT (+ 3.20185 MAST_ROTATION) 43.8301) "1" 0)
      (INSERT_DYNAMIC_PROPERTIES (ENTLAST) (LIST "ANR1") (LIST (+ MAST_ROTATION (* (/ PI 180) 33))))
      (INSERT_DYNAMIC_PROPERTIES (ENTLAST) '("Visibility1" ) (LIST "DOUBLE_LINE" ))
      (MODIFY_ATTRIBUTES (ENTLAST) (LIST "JUMPER_TYPE1") (LIST "G")) 
    )
  )

  (IF (/= (VL-POSITION INDENTIFICATION_STRING (LIST "ACC" "ACCFA" "ACCAEWA")) NIL)
    (PROGN
      (IF (= INDENTIFICATION_STRING "ACC") (COMMAND "INSERT" "ACC" (POLAR MAIN_BLOCK_INSERTION_POINT (+ (* 1 (/ PI 2)) MAST_ROTATION) 28.3) "1" MAST_ROTATION1))
      (IF (= INDENTIFICATION_STRING "ACCFA")
      (PROGN
      (COMMAND "INSERT" "ACC" (POLAR MAIN_BLOCK_INSERTION_POINT (+ (* 1 (/ PI 2)) MAST_ROTATION) 35) "1" MAST_ROTATION1)
      (COMMAND "INSERT" "BTB_ANC" (POLAR MAIN_BLOCK_INSERTION_POINT (+ (* 1 (/ PI 2)) MAST_ROTATION) 0.8) "1" MAST_ROTATION1)
      (MODIFY_ATTRIBUTES (ENTLAST) (LIST "ANCHOR_TYPE1" "ANCHOR_TYPE2") (LIST "FA" "FA"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (INSERT_DYNAMIC_PROPERTIES (ENTLAST) '("Visibility1") (LIST "WITHOUT WEIGHTS"))
      (COMMAND "INSERT" "JUMPER" (POLAR MAIN_BLOCK_INSERTION_POINT (+ (* 1 (/ PI 2)) MAST_ROTATION) 1) "1" MAST_ROTATION1)
      (INSERT_DYNAMIC_PROPERTIES (ENTLAST) '("Visibility1") (LIST "FJ/AEWA"))
      (MODIFY_ATTRIBUTES (ENTLAST) (LIST "JUMPER_TYPE1") (LIST "FJ"))
      (COMMAND "INSERT" "TENSION_LENGTH" (POLAR MAIN_BLOCK_INSERTION_POINT (+ (* 1 (/ PI 2)) MAST_ROTATION) 26.00) "1" MAST_ROTATION1)
      (COMMAND "INSERT" "TENSION_LENGTH" (POLAR MAIN_BLOCK_INSERTION_POINT (+ (* 1 (/ PI 2)) MAST_ROTATION) 26.00) "1" MAST_ROTATION1)
      (CHANGE_FLIP (ENTLAST) "TLF2")
      ;(INSERT_DYNAMIC_PROPERTIES (ENTLAST) '("TLM4 X") (LIST (+ (NTH 1 (NTH 0 (GET_DYNAMIC_PROPERTIES (ENTLAST) '("TLM4 X")))) 24.00)))
      )
      )
      (IF (= INDENTIFICATION_STRING "ACCAEWA")
      (PROGN
      (COMMAND "INSERT" "ACC" (POLAR MAIN_BLOCK_INSERTION_POINT (+ (* 1 (/ PI 2)) MAST_ROTATION) 35) "1" MAST_ROTATION1)
      (COMMAND "INSERT" "BTB_ANC" (POLAR MAIN_BLOCK_INSERTION_POINT (+ (* 1 (/ PI 2)) MAST_ROTATION) 0.8) "1" MAST_ROTATION1)
      (MODIFY_ATTRIBUTES (ENTLAST) (LIST "ANCHOR_TYPE1" "ANCHOR_TYPE2") (LIST "AEWA" "AEWA"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (INSERT_DYNAMIC_PROPERTIES (ENTLAST) '("Visibility1") (LIST "WITHOUT WEIGHTS"))
      (COMMAND "INSERT" "JUMPER" (POLAR MAIN_BLOCK_INSERTION_POINT (+ (* 1 (/ PI 2)) MAST_ROTATION) 1) "1" MAST_ROTATION1)
      (INSERT_DYNAMIC_PROPERTIES (ENTLAST) '("Visibility1") (LIST "FJ/AEWA"))
      (MODIFY_ATTRIBUTES (ENTLAST) (LIST "JUMPER_TYPE1") (LIST "AEWJ"))
      (COMMAND "INSERT" "TENSION_LENGTH" (POLAR MAIN_BLOCK_INSERTION_POINT (+ (* 1 (/ PI 2)) MAST_ROTATION) 26.00) "1" MAST_ROTATION1)
      (COMMAND "INSERT" "TENSION_LENGTH" (POLAR MAIN_BLOCK_INSERTION_POINT (+ (* 1 (/ PI 2)) MAST_ROTATION) 26.00) "1" MAST_ROTATION1)
      (CHANGE_FLIP (ENTLAST) "TLF2")
      ;(INSERT_DYNAMIC_PROPERTIES (ENTLAST) '("TLM4 X") (LIST (+ (NTH 1 (NTH 0 (GET_DYNAMIC_PROPERTIES (ENTLAST) '("TLM4 X")))) 24.00)))
      )
      )
      (COMMAND "INSERT" "JUMPER" (POLAR MAIN_BLOCK_INSERTION_POINT (+ 3.49063 MAST_ROTATION) 6.3218) "1" 0)
      (INSERT_DYNAMIC_PROPERTIES (ENTLAST) '( "ANR1") (LIST  (+ MAST_ROTATION (* (/ PI 180) 155))))
      (INSERT_DYNAMIC_PROPERTIES (ENTLAST) '("Visibility1" ) (LIST "SINGLE_LINE"))
      (MODIFY_ATTRIBUTES (ENTLAST) (LIST "JUMPER_TYPE1") (LIST "H"))
    )
  )


  (IF (/= (VL-POSITION INDENTIFICATION_STRING (LIST "AEWA" "DAEWA" "OLCAEWA")) NIL) 
    (PROGN
      (COMMAND "INSERT" "BTB_ANC" (POLAR MAIN_BLOCK_INSERTION_POINT (+ (* 1 (/ PI 2)) MAST_ROTATION) 0.8) "1" MAST_ROTATION1)
      (MODIFY_ATTRIBUTES (ENTLAST) (LIST "ANCHOR_TYPE1" "ANCHOR_TYPE2") (LIST "AEWA" "AEWA"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (INSERT_DYNAMIC_PROPERTIES (ENTLAST) '("Visibility1") (LIST "WITHOUT WEIGHTS"))
      (COMMAND "INSERT" "JUMPER" (POLAR MAIN_BLOCK_INSERTION_POINT (+ (* 1 (/ PI 2)) MAST_ROTATION) 1) "1" MAST_ROTATION1)
      (INSERT_DYNAMIC_PROPERTIES (ENTLAST) '("Visibility1") (LIST "FJ/AEWA"))
      (MODIFY_ATTRIBUTES (ENTLAST) (LIST "JUMPER_TYPE1") (LIST "AEWJ"))
      (IF (/= (VL-POSITION INDENTIFICATION_STRING (LIST "AEWA" "DAEWA")) NIL)
      (PROGN
      (COMMAND "INSERT" "TENSION_LENGTH" (POLAR MAIN_BLOCK_INSERTION_POINT (+ (* 1 (/ PI 2)) MAST_ROTATION) 35.00) "1" MAST_ROTATION1)
      (COMMAND "INSERT" "TENSION_LENGTH" (POLAR MAIN_BLOCK_INSERTION_POINT (+ (* 1 (/ PI 2)) MAST_ROTATION) 35.00) "1" MAST_ROTATION1)
      (CHANGE_FLIP (ENTLAST) "TLF2")
      ;(INSERT_DYNAMIC_PROPERTIES (ENTLAST) '("TLM4 X") (LIST (+ (NTH 1 (NTH 0 (GET_DYNAMIC_PROPERTIES (ENTLAST) '("TLM4 X")))) 24.00)))
      )
      (PROGN
      (COMMAND "INSERT" "TENSION_LENGTH" (POLAR MAIN_BLOCK_INSERTION_POINT (+ (* 1 (/ PI 2)) MAST_ROTATION) 50.00) "1" MAST_ROTATION1)
      (COMMAND "INSERT" "TENSION_LENGTH" (POLAR MAIN_BLOCK_INSERTION_POINT (+ (* 1 (/ PI 2)) MAST_ROTATION) 50.00) "1" MAST_ROTATION1)
      (CHANGE_FLIP (ENTLAST) "TLF2")
      ;(INSERT_DYNAMIC_PROPERTIES (ENTLAST) '("TLM4 X") (LIST (+ (NTH 1 (NTH 0 (GET_DYNAMIC_PROPERTIES (ENTLAST) '("TLM4 X")))) 24.00)))
      (COMMAND "INSERT" "OLC" (POLAR MAIN_BLOCK_INSERTION_POINT (+ (* 1 (/ PI 2)) MAST_ROTATION) 39.00) "1" MAST_ROTATION1)
      (MODIFY_ATTRIBUTES (ENTLAST) (LIST "TRACK") (LIST "FOR DN MAIN"))
      (COMMAND "INSERT" "JUMPER" (POLAR MAIN_BLOCK_INSERTION_POINT (+ 3.20185 MAST_ROTATION) 43.8301) "1" 0)
      (INSERT_DYNAMIC_PROPERTIES (ENTLAST) (LIST "ANR1") (LIST (+ MAST_ROTATION (* (/ PI 180) 33))))
      (INSERT_DYNAMIC_PROPERTIES (ENTLAST) '("Visibility1" ) (LIST "DOUBLE_LINE" ))
      (MODIFY_ATTRIBUTES (ENTLAST) (LIST "JUMPER_TYPE1") (LIST "G")) 
      )
      )
    )
  )


 (IF (/= (VL-POSITION INDENTIFICATION_STRING (LIST "FA" "DFA" "OLCFA")) NIL) 
    (PROGN
      (COMMAND "INSERT" "BTB_ANC" (POLAR MAIN_BLOCK_INSERTION_POINT (+ (* 1 (/ PI 2)) MAST_ROTATION) 0.8) "1" MAST_ROTATION1)
      (MODIFY_ATTRIBUTES (ENTLAST) (LIST "ANCHOR_TYPE1" "ANCHOR_TYPE2") (LIST "FA" "FA"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (INSERT_DYNAMIC_PROPERTIES (ENTLAST) '("Visibility1") (LIST "WITHOUT WEIGHTS"))
      (COMMAND "INSERT" "JUMPER" (POLAR MAIN_BLOCK_INSERTION_POINT (+ (* 1 (/ PI 2)) MAST_ROTATION) 1) "1" MAST_ROTATION1)
      (INSERT_DYNAMIC_PROPERTIES (ENTLAST) '("Visibility1") (LIST "FJ/AEWA"))
      (MODIFY_ATTRIBUTES (ENTLAST) (LIST "JUMPER_TYPE1") (LIST "FJ"))
      (IF (/= (VL-POSITION INDENTIFICATION_STRING (LIST "FA" "DFA")) NIL)
      (PROGN
      (COMMAND "INSERT" "TENSION_LENGTH" (POLAR MAIN_BLOCK_INSERTION_POINT (+ (* 1 (/ PI 2)) MAST_ROTATION) 35.00) "1" MAST_ROTATION1)
      (COMMAND "INSERT" "TENSION_LENGTH" (POLAR MAIN_BLOCK_INSERTION_POINT (+ (* 1 (/ PI 2)) MAST_ROTATION) 35.00) "1" MAST_ROTATION1)
      (CHANGE_FLIP (ENTLAST) "TLF2")
      ;(INSERT_DYNAMIC_PROPERTIES (ENTLAST) '("TLM4 X") (LIST (+ (NTH 1 (NTH 0 (GET_DYNAMIC_PROPERTIES (ENTLAST) '("TLM4 X")))) 24.00)))
      )
      (PROGN
      (COMMAND "INSERT" "TENSION_LENGTH" (POLAR MAIN_BLOCK_INSERTION_POINT (+ (* 1 (/ PI 2)) MAST_ROTATION) 50.00) "1" MAST_ROTATION1)
      (COMMAND "INSERT" "TENSION_LENGTH" (POLAR MAIN_BLOCK_INSERTION_POINT (+ (* 1 (/ PI 2)) MAST_ROTATION) 50.00) "1" MAST_ROTATION1)
      (CHANGE_FLIP (ENTLAST) "TLF2")
      ;(INSERT_DYNAMIC_PROPERTIES (ENTLAST) '("TLM4 X") (LIST (+ (NTH 1 (NTH 0 (GET_DYNAMIC_PROPERTIES (ENTLAST) '("TLM4 X")))) 24.00)))
      (COMMAND "INSERT" "OLC" (POLAR MAIN_BLOCK_INSERTION_POINT (+ (* 1 (/ PI 2)) MAST_ROTATION) 39.00) "1" MAST_ROTATION1)
      (MODIFY_ATTRIBUTES (ENTLAST) (LIST "TRACK") (LIST "FOR DN MAIN"))
      (COMMAND "INSERT" "JUMPER" (POLAR MAIN_BLOCK_INSERTION_POINT (+ 3.20185 MAST_ROTATION) 43.8301) "1" 0)
      (INSERT_DYNAMIC_PROPERTIES (ENTLAST) (LIST "ANR1") (LIST (+ MAST_ROTATION (* (/ PI 180) 33))))
      (INSERT_DYNAMIC_PROPERTIES (ENTLAST) '("Visibility1" ) (LIST "DOUBLE_LINE" ))
      (MODIFY_ATTRIBUTES (ENTLAST) (LIST "JUMPER_TYPE1") (LIST "G"))
      )
      )


    )
  )

  
 )
 )

;;;;;;;;;;;;;;;;;;;;;;;;;;

 (IF (= TRACK_TYPE "DN")
  (PROGN
  (IF (= INDENTIFICATION_STRING "BWA_END")
    (PROGN
      (COMMAND "INSERT" "ANCHOR" (POLAR MAIN_BLOCK_INSERTION_POINT (+ (* 3 (/ PI 2)) MAST_ROTATION) 0.8) "1" MAST_ROTATION1)
      (INSERT_DYNAMIC_PROPERTIES (ENTLAST) '("LENGTHEN") (LIST 3.00))
      (CHANGE_FLIP (ENTLAST) "ANF1")
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (COMMAND "INSERT" "TENSION_LENGTH" (POLAR MAIN_BLOCK_INSERTION_POINT (+ (* 3 (/ PI 2)) MAST_ROTATION) 24.125) "1" MAST_ROTATION1)
      (CHANGE_FLIP (ENTLAST) "TLF1")
      ;(INSERT_DYNAMIC_PROPERTIES (ENTLAST) '("TLM4 Y") (LIST (+ (NTH 1 (NTH 0 (GET_DYNAMIC_PROPERTIES (ENTLAST) '("TLM4 Y")))) 14.00)))
      (COMMAND "INSERT" "JUMPER" (POLAR MAIN_BLOCK_INSERTION_POINT (+ 3.05512 MAST_ROTATION) 7.6435) "1" 0)
      (INSERT_DYNAMIC_PROPERTIES (ENTLAST) (LIST "ANR1") (LIST (+ MAST_ROTATION (* (/ PI 180) 49))))
      (INSERT_DYNAMIC_PROPERTIES (ENTLAST) '("Visibility1") (LIST "ATJ"))
      (MODIFY_ATTRIBUTES (ENTLAST) (LIST "JUMPER_TYPE2") (LIST "3ATJ"))
    )
  )

  (IF (= INDENTIFICATION_STRING "BWA_START")
    (PROGN
      (COMMAND "INSERT" "ANCHOR" (POLAR MAIN_BLOCK_INSERTION_POINT (+ (* 3 (/ PI 2)) MAST_ROTATION) 0.8) "1" MAST_ROTATION1)
      (INSERT_DYNAMIC_PROPERTIES (ENTLAST) '("LENGTHEN") (LIST 3.00))
      
      (INSERT_ATTRIBUTES (ENTLAST) '("WIRE_RUN1") (LIST (LIST (- (CAR MAIN_BLOCK_INSERTION_POINT) 16.00)  (- (CADR MAIN_BLOCK_INSERTION_POINT) 5.75) 0.0)))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (COMMAND "INSERT" "TENSION_LENGTH" (POLAR MAIN_BLOCK_INSERTION_POINT (+ (* 3 (/ PI 2)) MAST_ROTATION) 24.125) "1" MAST_ROTATION1)
      (CHANGE_FLIP (ENTLAST) "TLF1")
      (CHANGE_FLIP (ENTLAST) "TLF2")
      ;(INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      (COMMAND "INSERT" "JUMPER" (POLAR MAIN_BLOCK_INSERTION_POINT (+ 0.142965 MAST_ROTATION) 7.6435) "1" 0)
      (INSERT_DYNAMIC_PROPERTIES (ENTLAST) (LIST "ANR1") (LIST (+ MAST_ROTATION (* (/ PI 180) 49))))
      (INSERT_DYNAMIC_PROPERTIES (ENTLAST) '("Visibility1") (LIST "ATJ"))
      (MODIFY_ATTRIBUTES (ENTLAST) (LIST "JUMPER_TYPE2") (LIST "3ATJ"))
    )
  )


  (IF (= INDENTIFICATION_STRING "ACA_END")
    (PROGN
      (COMMAND "INSERT" "ANCHOR" (POLAR MAIN_BLOCK_INSERTION_POINT (+ (* 3 (/ PI 2)) MAST_ROTATION) 0.8) "1" MAST_ROTATION1)
      (MODIFY_ATTRIBUTES (ENTLAST) (LIST "ANCHOR_TYPE1") (LIST "ACA"))
      (CHANGE_FLIP (ENTLAST) "ANF1")
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (INSERT_DYNAMIC_PROPERTIES (ENTLAST) '("LENGTHEN" "Visibility1") (LIST 4.00 "WITHOUT WEIGHTS"))
    )
  )


  (IF (= INDENTIFICATION_STRING "ACA_START")
    (PROGN
      (COMMAND "INSERT" "ANCHOR" (POLAR MAIN_BLOCK_INSERTION_POINT (+ (* 3 (/ PI 2)) MAST_ROTATION) 0.8) "1" MAST_ROTATION1)
      (INSERT_DYNAMIC_PROPERTIES (ENTLAST) '("LENGTHEN") (LIST 3.00))
      
      (MODIFY_ATTRIBUTES (ENTLAST) (LIST "ANCHOR_TYPE1") (LIST "ACA"))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (INSERT_DYNAMIC_PROPERTIES (ENTLAST) '("LENGTHEN" "Visibility1") (LIST 4.00 "WITHOUT WEIGHTS"))
      (INSERT_ATTRIBUTES (ENTLAST) '("WIRE_RUN1") (LIST (LIST (- (CAR MAIN_BLOCK_INSERTION_POINT) 16.00)  (- (CADR MAIN_BLOCK_INSERTION_POINT) 5.75) 0.0)))
    )
  )



  (IF (= INDENTIFICATION_STRING "OLC")
    (PROGN
      (COMMAND "INSERT" "OLC" (POLAR MAIN_BLOCK_INSERTION_POINT (+ (* 3 (/ PI 2)) MAST_ROTATION) 11.75) "1" MAST_ROTATION1)
      (COMMAND "INSERT" "JUMPER" (POLAR MAIN_BLOCK_INSERTION_POINT (+ 0.0604992 MAST_ROTATION)  40) "1" 0)
      (INSERT_DYNAMIC_PROPERTIES (ENTLAST) (LIST "ANR1") (LIST (+ MAST_ROTATION (* (/ PI 180) 389))))
      (INSERT_DYNAMIC_PROPERTIES (ENTLAST) '("Visibility1" ) (LIST "DOUBLE_LINE" ))
      (MODIFY_ATTRIBUTES (ENTLAST) (LIST "JUMPER_TYPE1") (LIST "G"))
      
    )
  )

  (IF (/= (VL-POSITION INDENTIFICATION_STRING (LIST "ACC" "ACCFA" "ACCAEWA")) NIL)
    (PROGN
    (IF (= INDENTIFICATION_STRING "ACC")
    (PROGN
      (COMMAND "INSERT" "ACC" (POLAR MAIN_BLOCK_INSERTION_POINT (+ (* 3 (/ PI 2)) MAST_ROTATION) 25.925) "1" MAST_ROTATION1)
      (INSERT_DYNAMIC_PROPERTIES (ENTLAST) '("ACF1") (LIST "1"))
      ;(INSERT_ATTRIBUTES (ENTLAST) '("MAST_COUNT1" "MAST_COUNT2" "ACC_NATURE") (LIST (LIST (- (CAR MAIN_BLOCK_INSERTION_POINT) 4.30)  (- (CADR MAIN_BLOCK_INSERTION_POINT) 49.85) 0.0) (LIST (+ (CAR MAIN_BLOCK_INSERTION_POINT) 2.00)  (- (CADR MAIN_BLOCK_INSERTION_POINT) 49.85) 0.0) (LIST (- (CAR MAIN_BLOCK_INSERTION_POINT) 10)  (- (CADR MAIN_BLOCK_INSERTION_POINT) 55.35) 0.0)))
      (MODIFY_ATTRIBUTES (ENTLAST) (LIST "ACC_NATURE") (LIST "ACC FOR UP MAIN"))
    )
    )
    (IF (= INDENTIFICATION_STRING "ACCFA")
      (PROGN
      (COMMAND "INSERT" "ACC" (POLAR MAIN_BLOCK_INSERTION_POINT (+ (* 3 (/ PI 2)) MAST_ROTATION) 30.925) "1" MAST_ROTATION1)
      (INSERT_DYNAMIC_PROPERTIES (ENTLAST) '("ACF1") (LIST "1"))
      ;(INSERT_ATTRIBUTES (ENTLAST) '("MAST_COUNT1" "MAST_COUNT2" "ACC_NATURE") (LIST (LIST (- (CAR MAIN_BLOCK_INSERTION_POINT) 4.30)  (- (CADR MAIN_BLOCK_INSERTION_POINT) 59.85) 0.0) (LIST (+ (CAR MAIN_BLOCK_INSERTION_POINT) 2.00)  (- (CADR MAIN_BLOCK_INSERTION_POINT) 59.85) 0.0) (LIST (- (CAR MAIN_BLOCK_INSERTION_POINT) 10)  (- (CADR MAIN_BLOCK_INSERTION_POINT) 63.85) 0.0)))
      (MODIFY_ATTRIBUTES (ENTLAST) (LIST "ACC_NATURE") (LIST "ACC FOR UP MAIN"))
      (COMMAND "INSERT" "BTB_ANC" (POLAR MAIN_BLOCK_INSERTION_POINT (+ (* 3 (/ PI 2)) MAST_ROTATION) 0.8) "1" MAST_ROTATION1)
      (MODIFY_ATTRIBUTES (ENTLAST) (LIST "ANCHOR_TYPE1" "ANCHOR_TYPE2") (LIST "FA" "FA"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (INSERT_DYNAMIC_PROPERTIES (ENTLAST) '("Visibility1") (LIST "WITHOUT WEIGHTS"))
      (COMMAND "INSERT" "JUMPER" (POLAR MAIN_BLOCK_INSERTION_POINT (+ (* 3 (/ PI 2)) MAST_ROTATION) 1) "1" MAST_ROTATION1)
      (INSERT_DYNAMIC_PROPERTIES (ENTLAST) '("Visibility1") (LIST "FJ/AEWA"))
      (MODIFY_ATTRIBUTES (ENTLAST) (LIST "JUMPER_TYPE1") (LIST "FJ"))
      (COMMAND "MIRROR" (ENTLAST) "" (POLAR MAIN_BLOCK_INSERTION_POINT (+ (* 3 (/ PI 2)) MAST_ROTATION) 1) (POLAR (POLAR MAIN_BLOCK_INSERTION_POINT (+ (* 3 (/ PI 2)) MAST_ROTATION) 1) MAST_ROTATION 1) "Y")
      (COMMAND "INSERT" "TENSION_LENGTH" (POLAR MAIN_BLOCK_INSERTION_POINT (+ (* 3 (/ PI 2)) MAST_ROTATION) 24.00) "1" MAST_ROTATION1)
      (CHANGE_FLIP (ENTLAST) "TLF1")
      ;(INSERT_DYNAMIC_PROPERTIES (ENTLAST) '("TLM4 Y") (LIST (+ (NTH 1 (NTH 0 (GET_DYNAMIC_PROPERTIES (ENTLAST) '("TLM4 Y")))) 12.50)))
      (COMMAND "INSERT" "TENSION_LENGTH" (POLAR MAIN_BLOCK_INSERTION_POINT (+ (* 3 (/ PI 2)) MAST_ROTATION) 24.00) "1" MAST_ROTATION1)
      (CHANGE_FLIP (ENTLAST) "TLF1")
      (CHANGE_FLIP (ENTLAST) "TLF2")
      ;(INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      )
    )

      (IF (= INDENTIFICATION_STRING "ACCAEWA")
      (PROGN
      (COMMAND "INSERT" "ACC" (POLAR MAIN_BLOCK_INSERTION_POINT (+ (* 3 (/ PI 2)) MAST_ROTATION) 30.925) "1" MAST_ROTATION1)
      (INSERT_DYNAMIC_PROPERTIES (ENTLAST) '("ACF1") (LIST "1"))
      (INSERT_ATTRIBUTES (ENTLAST) '("MAST_COUNT1" "MAST_COUNT2" "ACC_NATURE") (LIST (LIST (- (CAR MAIN_BLOCK_INSERTION_POINT) 4.30)  (- (CADR MAIN_BLOCK_INSERTION_POINT) 59.85) 0.0) (LIST (+ (CAR MAIN_BLOCK_INSERTION_POINT) 2.00)  (- (CADR MAIN_BLOCK_INSERTION_POINT) 59.85) 0.0) (LIST (- (CAR MAIN_BLOCK_INSERTION_POINT) 10)  (- (CADR MAIN_BLOCK_INSERTION_POINT) 63.85) 0.0)))
      (MODIFY_ATTRIBUTES (ENTLAST) (LIST "ACC_NATURE") (LIST "ACC FOR UP MAIN"))
      (COMMAND "INSERT" "BTB_ANC" (POLAR MAIN_BLOCK_INSERTION_POINT (+ (* 3 (/ PI 2)) MAST_ROTATION) 0.8) "1" MAST_ROTATION1)
      (MODIFY_ATTRIBUTES (ENTLAST) (LIST "ANCHOR_TYPE1" "ANCHOR_TYPE2") (LIST "AEWA" "AEWA"))
      (INSERT_DYNAMIC_PROPERTIES (ENTLAST) '("Visibility1") (LIST "WITHOUT WEIGHTS"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (COMMAND "INSERT" "JUMPER" (POLAR MAIN_BLOCK_INSERTION_POINT (+ (* 3 (/ PI 2)) MAST_ROTATION) 1) "1" MAST_ROTATION1)
      (INSERT_DYNAMIC_PROPERTIES (ENTLAST) '("Visibility1") (LIST "FJ/AEWA"))
      (MODIFY_ATTRIBUTES (ENTLAST) (LIST "JUMPER_TYPE1") (LIST "AEWJ"))
      (COMMAND "MIRROR" (ENTLAST) "" (POLAR MAIN_BLOCK_INSERTION_POINT (+ (* 3 (/ PI 2)) MAST_ROTATION) 1) (POLAR (POLAR MAIN_BLOCK_INSERTION_POINT (+ (* 3 (/ PI 2)) MAST_ROTATION) 1) MAST_ROTATION 1) "Y")
      (COMMAND "INSERT" "TENSION_LENGTH" (POLAR MAIN_BLOCK_INSERTION_POINT (+ (* 3 (/ PI 2)) MAST_ROTATION) 24.00) "1" MAST_ROTATION1)
      (CHANGE_FLIP (ENTLAST) "TLF1")
      ;(INSERT_DYNAMIC_PROPERTIES (ENTLAST) '("TLM4 Y") (LIST (+ (NTH 1 (NTH 0 (GET_DYNAMIC_PROPERTIES (ENTLAST) '("TLM4 Y")))) 12.50)))
      (COMMAND "INSERT" "TENSION_LENGTH" (POLAR MAIN_BLOCK_INSERTION_POINT (+ (* 3 (/ PI 2)) MAST_ROTATION) 24.00) "1" MAST_ROTATION1)
      (CHANGE_FLIP (ENTLAST) "TLF1")
      (CHANGE_FLIP (ENTLAST) "TLF2")
      ;(INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      
      )
      )
      (COMMAND "INSERT" "JUMPER" (POLAR MAIN_BLOCK_INSERTION_POINT (+ 0.34805 MAST_ROTATION) 6.3218) "1" 0)

      (INSERT_DYNAMIC_PROPERTIES (ENTLAST) '("ANR1") (LIST  (+ MAST_ROTATION (* (/ PI 180) 335))))
      (INSERT_DYNAMIC_PROPERTIES (ENTLAST) '("Visibility1") (LIST "SINGLE_LINE"))
      (MODIFY_ATTRIBUTES (ENTLAST) (LIST "JUMPER_TYPE1") (LIST "H"))
    
    )
     
  )
  
  
  (IF (/= (VL-POSITION INDENTIFICATION_STRING (LIST "AEWA" "DAEWA" "OLCAEWA")) NIL)
    (PROGN
      (COMMAND "INSERT" "BTB_ANC" (POLAR MAIN_BLOCK_INSERTION_POINT (+ (* 3 (/ PI 2)) MAST_ROTATION) 0.8) "1" MAST_ROTATION1)
      (MODIFY_ATTRIBUTES (ENTLAST) (LIST "ANCHOR_TYPE1" "ANCHOR_TYPE2") (LIST "AEWA" "AEWA"))
      (INSERT_DYNAMIC_PROPERTIES (ENTLAST) '("Visibility1") (LIST "WITHOUT WEIGHTS"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (COMMAND "INSERT" "JUMPER" (POLAR MAIN_BLOCK_INSERTION_POINT (+ (* 3 (/ PI 2)) MAST_ROTATION) 1) "1" MAST_ROTATION1)
      (INSERT_DYNAMIC_PROPERTIES (ENTLAST) '("Visibility1") (LIST "FJ/AEWA"))
      (MODIFY_ATTRIBUTES (ENTLAST) (LIST "JUMPER_TYPE1") (LIST "AEWJ"))
      (COMMAND "MIRROR" (ENTLAST) "" (POLAR MAIN_BLOCK_INSERTION_POINT (+ (* 3 (/ PI 2)) MAST_ROTATION) 1) (POLAR (POLAR MAIN_BLOCK_INSERTION_POINT (+ (* 3 (/ PI 2)) MAST_ROTATION) 1) MAST_ROTATION 1) "Y")
      (IF (/= (VL-POSITION INDENTIFICATION_STRING (LIST "AEWA" "DAEWA")) NIL)
      (PROGN
      (COMMAND "INSERT" "TENSION_LENGTH" (POLAR MAIN_BLOCK_INSERTION_POINT (+ (* 3 (/ PI 2)) MAST_ROTATION) 24.00) "1" MAST_ROTATION1)
      (CHANGE_FLIP (ENTLAST) "TLF1")
      ;(INSERT_DYNAMIC_PROPERTIES (ENTLAST) '("TLM4 Y") (LIST (+ (NTH 1 (NTH 0 (GET_DYNAMIC_PROPERTIES (ENTLAST) '("TLM4 Y")))) 12.50)))
      (COMMAND "INSERT" "TENSION_LENGTH" (POLAR MAIN_BLOCK_INSERTION_POINT (+ (* 3 (/ PI 2)) MAST_ROTATION) 24.00) "1" MAST_ROTATION1)
      (CHANGE_FLIP (ENTLAST) "TLF1")
      (CHANGE_FLIP (ENTLAST) "TLF2")
      ;(INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      )
      (PROGN
      (COMMAND "INSERT" "TENSION_LENGTH" (POLAR MAIN_BLOCK_INSERTION_POINT (+ (* 3 (/ PI 2)) MAST_ROTATION) 34.00) "1" MAST_ROTATION1)
      (CHANGE_FLIP (ENTLAST) "TLF1")
      ;(INSERT_DYNAMIC_PROPERTIES (ENTLAST) '("TLM4 Y") (LIST (+ (NTH 1 (NTH 0 (GET_DYNAMIC_PROPERTIES (ENTLAST) '("TLM4 Y")))) 12.50)))
      (COMMAND "INSERT" "TENSION_LENGTH" (POLAR MAIN_BLOCK_INSERTION_POINT (+ (* 3 (/ PI 2)) MAST_ROTATION) 34.00) "1" MAST_ROTATION1)
      (CHANGE_FLIP (ENTLAST) "TLF1")
      (CHANGE_FLIP (ENTLAST) "TLF2")
      ;(INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      (COMMAND "INSERT" "OLC" (POLAR MAIN_BLOCK_INSERTION_POINT (+ (* 3 (/ PI 2)) MAST_ROTATION) 10.00) "1" MAST_ROTATION1)
      (COMMAND "INSERT" "JUMPER" (POLAR MAIN_BLOCK_INSERTION_POINT (+ 0.0604992 MAST_ROTATION)  40) "1" 0)
      (INSERT_DYNAMIC_PROPERTIES (ENTLAST) (LIST "ANR1") (LIST (+ MAST_ROTATION (* (/ PI 180) 389))))
      (INSERT_DYNAMIC_PROPERTIES (ENTLAST) '("Visibility1" ) (LIST "DOUBLE_LINE" ))
      (MODIFY_ATTRIBUTES (ENTLAST) (LIST "JUMPER_TYPE1") (LIST "G"))
      )
      )

    )
  )


 (IF (/= (VL-POSITION INDENTIFICATION_STRING (LIST "FA" "DFA" "OLCFA")) NIL)
    (PROGN
      (COMMAND "INSERT" "BTB_ANC" (POLAR MAIN_BLOCK_INSERTION_POINT (+ (* 3 (/ PI 2)) MAST_ROTATION) 0.8) "1" MAST_ROTATION1)
      (MODIFY_ATTRIBUTES (ENTLAST) (LIST "ANCHOR_TYPE1" "ANCHOR_TYPE2") (LIST "FA" "FA"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (INSERT_DYNAMIC_PROPERTIES (ENTLAST) '("Visibility1") (LIST "WITHOUT WEIGHTS"))
      (COMMAND "INSERT" "JUMPER" (POLAR MAIN_BLOCK_INSERTION_POINT (+ (* 3 (/ PI 2)) MAST_ROTATION) 1) "1" MAST_ROTATION1)
      (INSERT_DYNAMIC_PROPERTIES (ENTLAST) '("Visibility1") (LIST "FJ/AEWA"))
      (MODIFY_ATTRIBUTES (ENTLAST) (LIST "JUMPER_TYPE1") (LIST "FJ"))
      (COMMAND "MIRROR" (ENTLAST) "" (POLAR MAIN_BLOCK_INSERTION_POINT (+ (* 3 (/ PI 2)) MAST_ROTATION) 1) (POLAR (POLAR MAIN_BLOCK_INSERTION_POINT (+ (* 3 (/ PI 2)) MAST_ROTATION) 1) MAST_ROTATION 1) "Y")
      (IF (/= (VL-POSITION INDENTIFICATION_STRING (LIST "FA" "DFA")) NIL)
      (PROGN
      (COMMAND "INSERT" "TENSION_LENGTH" (POLAR MAIN_BLOCK_INSERTION_POINT (+ (* 3 (/ PI 2)) MAST_ROTATION) 24.00) "1" MAST_ROTATION1)
      (CHANGE_FLIP (ENTLAST) "TLF1")
      ;(INSERT_DYNAMIC_PROPERTIES (ENTLAST) '("TLM4 Y") (LIST (+ (NTH 1 (NTH 0 (GET_DYNAMIC_PROPERTIES (ENTLAST) '("TLM4 Y")))) 12.50)))
      (COMMAND "INSERT" "TENSION_LENGTH" (POLAR MAIN_BLOCK_INSERTION_POINT (+ (* 3 (/ PI 2)) MAST_ROTATION) 24.00) "1" MAST_ROTATION1)
      (CHANGE_FLIP (ENTLAST) "TLF1")
      (CHANGE_FLIP (ENTLAST) "TLF2")
      ;(INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      )
      (PROGN
      (COMMAND "INSERT" "TENSION_LENGTH" (POLAR MAIN_BLOCK_INSERTION_POINT (+ (* 3 (/ PI 2)) MAST_ROTATION) 34.00) "1" MAST_ROTATION1)
      (CHANGE_FLIP (ENTLAST) "TLF1")
      ;(INSERT_DYNAMIC_PROPERTIES (ENTLAST) '("TLM4 Y") (LIST (+ (NTH 1 (NTH 0 (GET_DYNAMIC_PROPERTIES (ENTLAST) '("TLM4 Y")))) 12.50)))
      (COMMAND "INSERT" "TENSION_LENGTH" (POLAR MAIN_BLOCK_INSERTION_POINT (+ (* 3 (/ PI 2)) MAST_ROTATION) 34.00) "1" MAST_ROTATION1)
      (CHANGE_FLIP (ENTLAST) "TLF1")
      (CHANGE_FLIP (ENTLAST) "TLF2")
      ;(INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      (COMMAND "INSERT" "OLC" (POLAR MAIN_BLOCK_INSERTION_POINT (+ (* 3 (/ PI 2)) MAST_ROTATION) 10.00) "1" MAST_ROTATION1)
      (COMMAND "INSERT" "JUMPER" (POLAR MAIN_BLOCK_INSERTION_POINT (+ 0.0604992 MAST_ROTATION)  40) "1" 0)
      (INSERT_DYNAMIC_PROPERTIES (ENTLAST) (LIST "ANR1") (LIST (+ MAST_ROTATION (* (/ PI 180) 389))))
      (INSERT_DYNAMIC_PROPERTIES (ENTLAST) '("Visibility1" ) (LIST "DOUBLE_LINE" ))
      (MODIFY_ATTRIBUTES (ENTLAST) (LIST "JUMPER_TYPE1") (LIST "G"))
      )
      )

    )
  )
 )
  
 )
)






;;;;;;;;;;;;;;;;;;;;;;;;;;;;;;;;INSERT MAST COMMANDS;;;;;;;;;;;;;;;;;;;;;;;;;;;;;;;;;;;;;;;;;;;;;;;;;;;;;;;;;;;;;;;;;;;;;;;;;;;;;;


(DEFUN C:INSERT_MASTS_DNLINE ( / OFFSET_ENTITIES1 STARTING_OFFSET TRACK_ENTITY SNAP_POINTS SNAP_POINTS_SPAN INSERTION_POINTS_SPAN ENTNAME MAST_LENGTH AS I COLOUR_CODE INSERTION_POINT MAST_ROTATION CENTER_POINT )
(PROMPT "SELECT OFFSETS (OFFSET COLOUR CODE : GREEN->SINGLE CANTILEVER YELLOW->DOUBLE CANTILEVER")
(SETQ OFFSET_ENTITIES1 (SSGET))
(SETQ STARTING_OFFSET (CAR(ENTSEL "\nSELECT STARTING OFFSET:")))
(SETQ TRACK_ENTITY (CAR(ENTSEL "\nSELECT TRACK ALIGNMENT:")))
(SETQ ENTNAME (CAR(ENTSEL "\nSELECT REFERENCE MAST:")))
(SETQ OS_MODE (GETVAR "OSMODE"))
(SETQ 3DOS_MODE (GETVAR "3DOSMODE"))
(SETVAR "OSMODE" 0)
(SETVAR "3DOSMODE" 0)
(COMMAND "UCS" "W")
(SETQ SNAP_POINTS (GET_OFFSET_INTERSECTION_POINTS OFFSET_ENTITIES1 TRACK_ENTITY))
(SETQ SNAP_POINTS_SPAN (SPAN_FROM_OFFSETS TRACK_ENTITY (SORT_OFFSETS SNAP_POINTS STARTING_OFFSET) 1))
(SETQ INSERTION_POINTS_SPAN (GET_MAST_INSERTION_POINT_GPS_LEFT TRACK_ENTITY SNAP_POINTS_SPAN (N_ELE_LIST 3.00 (LENGTH SNAP_POINTS_SPAN)) 1))
(SETQ MAST_LENGTH (GET_DYNAMIC_PROPERTIES ENTNAME '("STL1")))
(SETQ AS (GET_DYNAMIC_PROPERTIES ENTNAME '("SGM1 X" "IMM1 X" "SGM1 Y" "IMM1 Y" "LEAD-LENGTH" "LEAD-ANGLE")))
(SETQ I 0 COLOUR_CODE NIL INSERTION_POINT NIL MAST_ROTATION NIL CENTER_POINT NIL)
(WHILE (< I (LENGTH INSERTION_POINTS_SPAN))
(SETQ COLOUR_CODE (CDR (ASSOC 62  (ENTGET (NTH 0 (NTH I INSERTION_POINTS_SPAN))))))
  (IF (= COLOUR_CODE 3)
    (PROGN
(SETQ INSERTION_POINT (NTH 3 (NTH I INSERTION_POINTS_SPAN)))
(COMMAND "INSERT" "SINGLE_CANT_MAST" INSERTION_POINT "1" "0" )
(COMMAND "ROTATE" (ENTLAST) "" INSERTION_POINT "R" INSERTION_POINT (POLAR INSERTION_POINT (/ (* 3 PI) 2) 1) "P" (NTH 3 (NTH I INSERTION_POINTS_SPAN)) (NTH 1 (NTH I INSERTION_POINTS_SPAN)))
(IF (/= I (- (LENGTH SNAP_POINTS) 1)) (PROGN (MODIFY_ATTRIBUTES (ENTLAST) '("SPAN1") (LIST (NTH 2 (NTH I INSERTION_POINTS_SPAN))))))
(INSERT_DYNAMIC_PROPERTIES (ENTLAST) (SINGLE_ELE_LIST AS 0) (SINGLE_ELE_LIST AS 1))
(SETQ MAST_ROTATION (VLAX-GET-PROPERTY (VLAX-ENAME->VLA-OBJECT (ENTLAST)) 'ROTATION))
(SETQ CENTER_POINT (NTH 0 (TRANSFORM (BUILD_LIST (FILTER_LIST (LIST "CIRCLE") (BLOCK_ENAME1 (ENTLAST)) 1) (LIST 3 4 5)) INSERTION_POINT MAST_ROTATION)))
(COMMAND "INSERT" "SUPER_MAST" CENTER_POINT "1" (* (/ 180 PI) MAST_ROTATION))
(CHANGE_FLIP (ENTLAST) "STF1")
;(INSERT_ATTRIBUTES (ENTLAST) '("SPAN1") (LIST (LIST (+ (CAR INSERTION_POINT) (* (/ (NTH 1 (NTH I SNAP_POINTS)) 2) SCALE))  (+ (CADR INSERTION_POINT) SPAN_REFERENCE) 0.0)))
)
  )

(IF (= COLOUR_CODE 2)
    (PROGN
(SETQ INSERTION_POINT (NTH 3 (NTH I INSERTION_POINTS_SPAN)))
(COMMAND "INSERT" "DOUBLE_CANT_MAST" INSERTION_POINT "1" "0" )
(COMMAND "ROTATE" (ENTLAST) "" INSERTION_POINT "R" INSERTION_POINT (POLAR INSERTION_POINT (/ (* 3 PI) 2) 1) "P" (NTH 3 (NTH I INSERTION_POINTS_SPAN)) (NTH 1 (NTH I INSERTION_POINTS_SPAN)))
(IF (/= I (- (LENGTH SNAP_POINTS) 1)) (PROGN (MODIFY_ATTRIBUTES (ENTLAST) '("SPAN1" "SPAN2") (LIST (NTH 2 (NTH I INSERTION_POINTS_SPAN)) (NTH 2 (NTH I INSERTION_POINTS_SPAN))))))
(INSERT_DYNAMIC_PROPERTIES (ENTLAST) (SINGLE_ELE_LIST AS 0) (SINGLE_ELE_LIST AS 1))
(SETQ MAST_ROTATION (VLAX-GET-PROPERTY (VLAX-ENAME->VLA-OBJECT (ENTLAST)) 'ROTATION))
(SETQ CENTER_POINT (NTH 0 (TRANSFORM (BUILD_LIST (FILTER_LIST (LIST "CIRCLE") (BLOCK_ENAME1 (ENTLAST)) 1) (LIST 3 4 5)) INSERTION_POINT MAST_ROTATION)))
(COMMAND "INSERT" "SUPER_MAST" CENTER_POINT "1" (* (/ 180 PI) MAST_ROTATION))
(CHANGE_FLIP (ENTLAST) "STF1")
;(INSERT_ATTRIBUTES (ENTLAST) '("SPAN1") (LIST (LIST (+ (CAR INSERTION_POINT) (* (/ (NTH 1 (NTH I SNAP_POINTS)) 2) SCALE))  (+ (CADR INSERTION_POINT) SPAN_REFERENCE) 0.0)))

)
  )
(SETQ I (+ I 1))
)
(SETVAR "OSMODE" OS_MODE)
(SETVAR "3DOSMODE" 3DOS_MODE)
(COMMAND "UCS" "P")
)






(DEFUN C:INSERT_MASTS_UPLINE ( / OFFSET_ENTITIES1 STARTING_OFFSET TRACK_ENTITY SNAP_POINTS SNAP_POINTS_SPAN INSERTION_POINTS_SPAN ENTNAME MAST_LENGTH AS I COLOUR_CODE INSERTION_POINT MAST_ROTATION CENTER_POINT )
(PROMPT "SELECT OFFSETS (OFFSET COLOUR CODE : GREEN->SINGLE CANTILEVER YELLOW->DOUBLE CANTILEVER")
(SETQ OFFSET_ENTITIES1 (SSGET))
(SETQ STARTING_OFFSET (CAR(ENTSEL "\nSELECT STARTING OFFSET:")))
(SETQ TRACK_ENTITY (CAR(ENTSEL "\nSELECT TRACK ALIGNMENT:")))
(SETQ ENTNAME (CAR(ENTSEL "\nSELECT REFERENCE MAST:")))
(SETQ OS_MODE (GETVAR "OSMODE"))
(SETQ 3DOS_MODE (GETVAR "3DOSMODE"))
(SETVAR "OSMODE" 0)
(SETVAR "3DOSMODE" 0)
(COMMAND "UCS" "W")
(SETQ SNAP_POINTS (GET_OFFSET_INTERSECTION_POINTS OFFSET_ENTITIES1 TRACK_ENTITY))
(SETQ SNAP_POINTS_SPAN (SPAN_FROM_OFFSETS TRACK_ENTITY (SORT_OFFSETS SNAP_POINTS STARTING_OFFSET) 1))
(SETQ INSERTION_POINTS_SPAN (GET_MAST_INSERTION_POINT_GPS_RIGHT TRACK_ENTITY SNAP_POINTS_SPAN (N_ELE_LIST 3.00 (LENGTH SNAP_POINTS_SPAN)) 1))
(SETQ MAST_LENGTH (GET_DYNAMIC_PROPERTIES ENTNAME '("STL1")))
(SETQ AS (GET_DYNAMIC_PROPERTIES ENTNAME '("SGM1 X" "IMM1 X" "SGM1 Y" "IMM1 Y" "LEAD-LENGTH" "LEAD-ANGLE")))
(SETQ I 0 COLOUR_CODE NIL INSERTION_POINT NIL MAST_ROTATION NIL CENTER_POINT NIL)
(WHILE (< I (LENGTH INSERTION_POINTS_SPAN))
(SETQ COLOUR_CODE (CDR (ASSOC 62  (ENTGET (NTH 0 (NTH I INSERTION_POINTS_SPAN))))))
  (IF (= COLOUR_CODE 3)
    (PROGN
(SETQ INSERTION_POINT (NTH 3 (NTH I INSERTION_POINTS_SPAN)))
(COMMAND "INSERT" "SINGLE_CANT_MAST" INSERTION_POINT "1" "0" )
(CHANGE_FLIP (ENTLAST) "STF1")
(COMMAND "ROTATE" (ENTLAST) "" INSERTION_POINT "R" INSERTION_POINT (POLAR INSERTION_POINT (/ PI 2) 1) "P" (NTH 3 (NTH I INSERTION_POINTS_SPAN)) (NTH 1 (NTH I INSERTION_POINTS_SPAN)))
(IF (/= I (- (LENGTH SNAP_POINTS) 1)) (PROGN (MODIFY_ATTRIBUTES (ENTLAST) '("SPAN1") (LIST (NTH 2 (NTH I INSERTION_POINTS_SPAN))))))
(INSERT_DYNAMIC_PROPERTIES (ENTLAST) (SINGLE_ELE_LIST AS 0) (SINGLE_ELE_LIST AS 1))
(SETQ MAST_ROTATION (VLAX-GET-PROPERTY (VLAX-ENAME->VLA-OBJECT (ENTLAST)) 'ROTATION))
(SETQ CENTER_POINT (NTH 0 (TRANSFORM (BUILD_LIST (FILTER_LIST (LIST "CIRCLE") (BLOCK_ENAME1 (ENTLAST)) 1) (LIST 3 4 5)) INSERTION_POINT MAST_ROTATION)))
(COMMAND "INSERT" "SUPER_MAST" CENTER_POINT "1" (* (/ 180 PI) MAST_ROTATION))
;(INSERT_ATTRIBUTES (ENTLAST) '("SPAN1") (LIST (LIST (+ (CAR INSERTION_POINT) (* (/ (NTH 1 (NTH I SNAP_POINTS)) 2) SCALE))  (+ (CADR INSERTION_POINT) SPAN_REFERENCE) 0.0)))
)
  )

(IF (= COLOUR_CODE 2)
    (PROGN
(SETQ INSERTION_POINT (NTH 3 (NTH I INSERTION_POINTS_SPAN)))
(COMMAND "INSERT" "DOUBLE_CANT_MAST" INSERTION_POINT "1" "0" )
(CHANGE_FLIP (ENTLAST) "STF1")
(COMMAND "ROTATE" (ENTLAST) "" INSERTION_POINT "R" INSERTION_POINT (POLAR INSERTION_POINT (/ PI 2) 1) "P" (NTH 3 (NTH I INSERTION_POINTS_SPAN)) (NTH 1 (NTH I INSERTION_POINTS_SPAN)))
(IF (/= I (- (LENGTH SNAP_POINTS) 1)) (PROGN (MODIFY_ATTRIBUTES (ENTLAST) '("SPAN1" "SPAN2") (LIST (NTH 2 (NTH I INSERTION_POINTS_SPAN)) (NTH 2 (NTH I INSERTION_POINTS_SPAN))))))
(INSERT_DYNAMIC_PROPERTIES (ENTLAST) (SINGLE_ELE_LIST AS 0) (SINGLE_ELE_LIST AS 1))
(SETQ MAST_ROTATION (VLAX-GET-PROPERTY (VLAX-ENAME->VLA-OBJECT (ENTLAST)) 'ROTATION))
(SETQ CENTER_POINT (NTH 0 (TRANSFORM (BUILD_LIST (FILTER_LIST (LIST "CIRCLE") (BLOCK_ENAME1 (ENTLAST)) 1) (LIST 3 4 5)) INSERTION_POINT MAST_ROTATION)))
(COMMAND "INSERT" "SUPER_MAST" CENTER_POINT "1" (* (/ 180 PI) MAST_ROTATION))
;(INSERT_ATTRIBUTES (ENTLAST) '("SPAN1") (LIST (LIST (+ (CAR INSERTION_POINT) (* (/ (NTH 1 (NTH I SNAP_POINTS)) 2) SCALE))  (+ (CADR INSERTION_POINT) SPAN_REFERENCE) 0.0)))
)
  )
(SETQ I (+ I 1))
)
(SETVAR "OSMODE" OS_MODE)
(SETVAR "3DOSMODE" 3DOS_MODE)
(COMMAND "UCS" "P")
)
;;;;;;;;;;;;;;;;;;;;;;;;;;;;;;;;;;;;;;SUPPORTING FUNCTIONS FOR INSERT_MASTS FUNCTIONS;;;;;;;;;;;;;;;;;;;;;;;;;;;;;;;;;;;;;;;;;;;;;;;;;;;;;;;;;;;;;;;;;;;;;;;;;;;;;;;;;;;;;;;;;;;;;;;;;;;;;;

(DEFUN SORT_OFFSETS (ENT_LIST STARTING_ENTITY / I TEMP_DIST FINAL_LIST )
  (SETQ TEMP_ENTITY (ASSOC STARTING_ENTITY ENT_LIST))
  (SETQ I 0 TEMP_DIST NIL FINAL_LIST NIL)
  (WHILE (< I (LENGTH ENT_LIST))
    (SETQ TEMP_DIST (DISTANCE (NTH 1 TEMP_ENTITY) (NTH 1 (NTH I ENT_LIST))))
    (SETQ FINAL_LIST (CONS (APPEND (NTH I ENT_LIST) (LIST TEMP_DIST)) FINAL_LIST))
    (SETQ I (+ I 1))
  )
  (BUILD_LIST (SORT_FUN (REVERSE FINAL_LIST) 0 2) (LIST 0 1))
)


(DEFUN SPAN_FROM_OFFSETS (TRACK_CENTER INTERSECTION_POINT FLAG / I TEMP_SPAN FINAL_LIST)
  (SETQ I 0 TEMP_SPAN NIL FINAL_LIST NIL)
  (WHILE (< I (LENGTH INTERSECTION_POINT))
    (IF (/= I (- (LENGTH INTERSECTION_POINT) 1)) (SETQ TEMP_SPAN (RTOS (APPROXIMATE_SPAN (DISTANCE_ON_CURVE_GPS TRACK_CENTER (NTH FLAG (NTH I INTERSECTION_POINT)) (NTH FLAG (NTH (+ I 1) INTERSECTION_POINT))) 0.68) 2 2)) (SETQ TEMP_SPAN NIL))
    (SETQ FINAL_LIST (CONS (APPEND (NTH I INTERSECTION_POINT) (LIST TEMP_SPAN)) FINAL_LIST))
    (SETQ I (+ I 1))
  )
  (REVERSE FINAL_LIST)
)


(DEFUN GET_OFFSET_INTERSECTION_POINTS ( OFFSET_ENTITIES1 TRACK_ENTITY / OFFSET_ENTITIES TRACK_ENTITY I TEMP_ELE1 TEMP_ELE2 LIST2 )

  (SETQ OFFSET_ENTITIES1 (FORM_SSSET OFFSET_ENTITIES1))
  (SETQ I 0)
  (SETQ OFFSET_ENTITIES NIL)
  (WHILE (< I (LENGTH OFFSET_ENTITIES1))
    (SETQ TEMP_ELE1 (CDR (ASSOC 10 (ENTGET (NTH I OFFSET_ENTITIES1)))))
    (SETQ OFFSET_ENTITIES (CONS (LIST (NTH I OFFSET_ENTITIES1) TEMP_ELE1) OFFSET_ENTITIES))
    (SETQ I (+ I 1))
  )
  (SETQ OFFSET_ENTITIES (REVERSE OFFSET_ENTITIES))
  (SETQ OFFSET_ENTITIES (SORT_FUN OFFSET_ENTITIES 1 0))
  
  (SETQ I 0)
  (SETQ TEMP_ELE1 NIL)
  (SETQ TEMP_ELE2 NIL)
  (SETQ LIST2 NIL)
  (WHILE (< I (LENGTH OFFSET_ENTITIES))
  ;(SETQ TEMP_ELE1 (NTH 0 (ACET-GEOM-INTERSECTWITH TRACK_ENTITY (NTH 0 (NTH I OFFSET_ENTITIES)) 0.0000001)))
  (SETQ TEMP_ELE1 (VLAX-SAFEARRAY->LIST (VLAX-VARIANT-VALUE (VLA-INTERSECTWITH (VLAX-ENAME->VLA-OBJECT TRACK_ENTITY) (VLAX-ENAME->VLA-OBJECT (NTH 0 (NTH I OFFSET_ENTITIES))) ACEXTENDNONE))))
  (SETQ TEMP_ELE2 (LIST (NTH 0 TEMP_ELE1) (NTH 1 TEMP_ELE1) (NTH 2 TEMP_ELE1)))
  (IF (/= (VLAX-CURVE-GETDISTATPOINT TRACK_ENTITY TEMP_ELE2)  NIL)
    (SETQ TEMP_ELE1 TEMP_ELE2)
    (SETQ TEMP_ELE1 (LIST (NTH 3 TEMP_ELE1) (NTH 4 TEMP_ELE1) (NTH 5 TEMP_ELE1)))
  )
  (SETQ LIST2 (CONS (LIST (NTH 0 (NTH I OFFSET_ENTITIES)) TEMP_ELE1) LIST2))
  (SETQ I (+ I 1))
  )
  (SORT_FUN (REVERSE LIST2) 1 0)
)

(DEFUN GET_SLOPE ( POLYLINE_ENTITY POINT / ANGLE1 DERIVATIVE SLOPE)
(SETQ POLYLINE_ANGLE (ANGLE (VLAX-CURVE-GETSTARTPOINT POLYLINE_ENTITY) (VLAX-CURVE-GETPOINTATDIST POLYLINE_ENTITY 50)))
(IF (<= POLYLINE_ANGLE PI) (SETQ DIRECTION "POSITIVE") (SETQ DIRECTION "NEGATIVE"))
(SETQ ANGLE1 (VLAX-CURVE-GETPARAMATPOINT POLYLINE_ENTITY POINT))
(SETQ DERIVATIVE (VLAX-CURVE-GETFIRSTDERIV POLYLINE_ENTITY ANGLE1))
(LIST (ANGLE '(0 0 0) DERIVATIVE) DIRECTION)
)


(DEFUN GET_MAST_INSERTION_POINT_GPS_LEFT ( POLYLINE_ENTITY POINT_LIST DIST_LIST FLAG / I SLOPE_INFO NORMAL_SLOPE TEMP_ELE FINAL_LIST )
(SETQ POLYLINE_ENTITY (VLAX-ENAME->VLA-OBJECT POLYLINE_ENTITY))
(SETQ I 0 SLOPE_INFO NIL NORMAL_SLOPE NIL TEMP_ELE NIL FINAL_LIST NIL)
(WHILE (< I (LENGTH POINT_LIST))
(SETQ SLOPE_INFO (GET_SLOPE POLYLINE_ENTITY (NTH FLAG (NTH I POINT_LIST))))
(IF (= (NTH 1 SLOPE_INFO) "POSITIVE")
  (SETQ NORMAL_SLOPE (+ (/ PI 2) (NTH 0 SLOPE_INFO)))
  (SETQ NORMAL_SLOPE (+ (* 3 (/ PI 2)) (NTH 0 SLOPE_INFO)))
)
(SETQ TEMP_ELE (POLAR (NTH FLAG (NTH I POINT_LIST)) NORMAL_SLOPE (NTH I DIST_LIST)))
(SETQ FINAL_LIST (CONS (APPEND (NTH I POINT_LIST) (LIST TEMP_ELE)) FINAL_LIST))
(SETQ I (+ I 1))
)
(REVERSE FINAL_LIST)
)


(DEFUN GET_MAST_INSERTION_POINT_GPS_RIGHT ( POLYLINE_ENTITY POINT_LIST DIST_LIST FLAG / I SLOPE_INFO NORMAL_SLOPE TEMP_ELE FINAL_LIST )
(SETQ POLYLINE_ENTITY (VLAX-ENAME->VLA-OBJECT POLYLINE_ENTITY))
(SETQ I 0 SLOPE_INFO NIL NORMAL_SLOPE NIL TEMP_ELE NIL FINAL_LIST NIL)
(WHILE (< I (LENGTH POINT_LIST))
(SETQ SLOPE_INFO (GET_SLOPE POLYLINE_ENTITY (NTH FLAG (NTH I POINT_LIST))))
(IF (= (NTH 1 SLOPE_INFO) "NEGATIVE")
  (SETQ NORMAL_SLOPE (+ (/ PI 2) (NTH 0 SLOPE_INFO)))
  (SETQ NORMAL_SLOPE (+ (* 3 (/ PI 2)) (NTH 0 SLOPE_INFO)))
)
(SETQ TEMP_ELE (POLAR (NTH FLAG (NTH I POINT_LIST)) NORMAL_SLOPE (NTH I DIST_LIST)))
(SETQ FINAL_LIST (CONS (APPEND (NTH I POINT_LIST) (LIST TEMP_ELE)) FINAL_LIST))
(SETQ I (+ I 1))
)
(REVERSE FINAL_LIST)
)


;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;




;;;;;;;;;;;;;;;;;;;;;;;;;;;;;;;;;;;;;;;;;;;;;;;;;;;;;;;;;;;;;;;;MATCH BLOCKS;;;;;;;;;;;;;;;;;;;;;;;;;;;;;;;;;;;;;;;;;;;;;;;;;;;;;;;;;;;;;;;;;;;;;;;;;;;;;;;;;;;;;;;;;;;;;;;;;;;;;;;;;


;;;;;;;;;;;;;;;;;;;;;;;;;;;;;;;;;;;;;;;;;;;;;;;;;;;;;;;;;;;;;;;;;;;;;;;;;;;;;MATCH BLOCKS FUNCTIONS;;;;;;;;;;;;;;;;;;;;;;;;;;;;;;;;;;;;;;;;;;;;;;;;;;;;;;;;;;;;;;;;;;;;;;;;;;;;;;;;;;;;;;;;;;;;;;;;;;;;;;;;;;;;;;;;;;;
  



  



(DEFUN C:MATCH_BLOCKS_GPS ( / ENTNAME SSSET ENT_LIST ENT_INFO MAST_NUMBER MAST_NUMBER_X MAST_NUMBER_Y FDN_REFERENCE FINAL_VALUES FDN_REFERENCE_X FDN_REFERENCE_Y RD_REFERENCE RD_REFERENCE_X RD_REFERENCE_Y TC_REFERENCE TC_REFERENCE_X TC_REFERENCE_Y SPAN_REFERENCE_X SPAN_REFERENCE_Y BS_PT VALUES VALUES1 VALUES2 VALUES3 VALUES4 VALUES5 POINT POINT1 POINT2 POINT3 POINT4 POINT5 VISIBILITY_SPAN VISIBILITY_TC VISIBILITY_FDN VISIBILITY_RD I BASE_POINT TEMP_SPAN) 
  (SETQ ENTNAME (CAR(ENTSEL "SELECT REFERENCE MAST:")))
  ;(SETQ BS_PT (CDR (ASSOC 10 (ENTGET ENTNAME))))
  (PROMPT "/N SELECT BLOCKS TO MATCH")
  (SETQ SSSET (SSGET))
  (COMMAND "UCS" "W")
  (SETQ ENT_LIST (FORM_SSSET SSSET))
  (SETQ ENT_LIST (EXTRACT_ENTITY_INFO ENT_LIST 1 3))
  (SETQ ENT_LIST (SORT_FUN ENT_LIST 1 0))
  (SETQ ENT_LIST (SINGLE_ELE_LIST ENT_LIST 0))
  (SETQ ENT_INFO (YARD_STRUCTURE_INFO ENTNAME))

  (SETQ MAST_NUMBER (GET_TEXT_ALIGNMENT_POINT (LIST ENTNAME) "MAST_NUMBER_LINK1" 0))
  (SETQ MAST_NUMBER_X (- (NTH 0 (NTH 1 (NTH 0 MAST_NUMBER))) (NTH 0 (CDR (ASSOC 10 (ENTGET ENTNAME))))))
  (SETQ MAST_NUMBER_Y (- (NTH 1 (NTH 1 (NTH 0 MAST_NUMBER))) (NTH 1 (CDR (ASSOC 10 (ENTGET ENTNAME))))))
  
  (SETQ TC_REFERENCE (GET_TEXT_ALIGNMENT_POINT (LIST ENTNAME) "TC1" 0))
  (SETQ TC_REFERENCE_X (- (NTH 0 (NTH 1 (NTH 0 TC_REFERENCE))) (NTH 0 (CDR (ASSOC 10 (ENTGET ENTNAME))))))
  (SETQ TC_REFERENCE_Y (- (NTH 1 (NTH 1 (NTH 0 TC_REFERENCE))) (NTH 1 (CDR (ASSOC 10 (ENTGET ENTNAME))))))
  
  (SETQ SPAN_REFERENCE (GET_TEXT_ALIGNMENT_POINT (LIST ENTNAME) "SPAN1" 0))
  (SETQ SPAN_REFERENCE_X (- (NTH 0 (NTH 1 (NTH 0 SPAN_REFERENCE))) (NTH 0 (CDR (ASSOC 10 (ENTGET ENTNAME))))))
  (SETQ SPAN_REFERENCE_Y (- (NTH 1 (NTH 1 (NTH 0 SPAN_REFERENCE))) (NTH 1 (CDR (ASSOC 10 (ENTGET ENTNAME))))))
  
  
  (SETQ FDN_REFERENCE (GET_TEXT_ALIGNMENT_POINT (LIST ENTNAME) "FOUNDATION_TYPE1" 0))
  (SETQ FDN_REFERENCE_X (- (NTH 0 (NTH 1 (NTH 0 FDN_REFERENCE))) (NTH 0 (CDR (ASSOC 10 (ENTGET ENTNAME))))))
  (SETQ FDN_REFERENCE_Y (- (NTH 1 (NTH 1 (NTH 0 FDN_REFERENCE))) (NTH 1 (CDR (ASSOC 10 (ENTGET ENTNAME))))))
  
  (SETQ RD_REFERENCE (GET_TEXT_ALIGNMENT_POINT (LIST ENTNAME) "RD1" 0))
  (SETQ RD_REFERENCE_X (- (NTH 0 (NTH 1 (NTH 0 RD_REFERENCE))) (NTH 0 (CDR (ASSOC 10 (ENTGET ENTNAME))))))
  (SETQ RD_REFERENCE_Y (- (NTH 1 (NTH 1 (NTH 0 RD_REFERENCE))) (NTH 1 (CDR (ASSOC 10 (ENTGET ENTNAME))))))
  
  (SETQ DFCC_CTN_CHAINAGE_REFERENCE (GET_TEXT_ALIGNMENT_POINT (LIST ENTNAME) "DFCC_CTN_CHAINAGE1" 0))
  (SETQ DFCC_CTN_CHAINAGE_REFERENCE_X (- (NTH 0 (NTH 1 (NTH 0 DFCC_CTN_CHAINAGE_REFERENCE))) (NTH 0 (CDR (ASSOC 10 (ENTGET ENTNAME))))))
  (SETQ DFCC_CTN_CHAINAGE_REFERENCE_Y (- (NTH 1 (NTH 1 (NTH 0 DFCC_CTN_CHAINAGE_REFERENCE))) (NTH 1 (CDR (ASSOC 10 (ENTGET ENTNAME))))))
  
  (SETQ IR_CHAINAGE_REFERENCE (GET_TEXT_ALIGNMENT_POINT (LIST ENTNAME) "IR_CHAINAGE1" 0))
  (SETQ IR_CHAINAGE_REFERENCE_X (- (NTH 0 (NTH 1 (NTH 0 IR_CHAINAGE_REFERENCE))) (NTH 0 (CDR (ASSOC 10 (ENTGET ENTNAME))))))
  (SETQ IR_CHAINAGE_REFERENCE_Y (- (NTH 1 (NTH 1 (NTH 0 IR_CHAINAGE_REFERENCE))) (NTH 1 (CDR (ASSOC 10 (ENTGET ENTNAME))))))

 ;;NEWLY ADDED

  
  (SETQ FINAL_VALUES (GET_DYNAMIC_PROPERTIES ENTNAME (LIST "LNM1 X" "LNM1 Y" "LCM1 X" "LCM1 Y" "LTM1 X" "LTM1 Y")))
  


  ;;
  
  (SETQ REFERENCE_LIST (LIST (LIST MAST_NUMBER_X MAST_NUMBER_Y 0.0) (LIST TC_REFERENCE_X TC_REFERENCE_Y 0.0) (LIST SPAN_REFERENCE_X SPAN_REFERENCE_Y 0.0)))
  (SETQ REFERENCE_LIST1 (LIST (LIST FDN_REFERENCE_X FDN_REFERENCE_Y 0.0) (LIST RD_REFERENCE_X RD_REFERENCE_Y 0.0) (LIST DFCC_CTN_CHAINAGE_REFERENCE_X DFCC_CTN_CHAINAGE_REFERENCE_Y 0.0) (LIST IR_CHAINAGE_REFERENCE_X IR_CHAINAGE_REFERENCE_Y 0.0)))
  ;(SETQ BS_PT (CDR (ASSOC 10 (ENTGET ENTNAME))))
  ;(SETQ AS (GET_DYNAMIC_PROPERTIES ENTNAME '("SGM1 X" "IMM1 X" "SGM1 Y" "IMM1 Y" "LEAD-ANGLE")))
  (SETQ REFERENCE_LEAD_LENGTH (NTH 1 (NTH 0 (GET_DYNAMIC_PROPERTIES ENTNAME '("LEAD-LENGTH")))))
  (SETQ REFERENCE_IMPLANTATION (ATOF (NTH 0 (SINGLE_ELE_LIST (EXTRACT_ATTRIBUTES ENTNAME (LIST "IMPLANTATION1" ) 1) 1))))
  (SETQ BASE_ROTATION (VLAX-GET-PROPERTY (VLAX-ENAME->VLA-OBJECT ENTNAME) 'ROTATION))

  (SETQ VISIBILITY_SPAN (NTH 0 (SINGLE_ELE_LIST (EXTRACT_ATTRIBUTES ENTNAME (LIST "SPAN1" ) 3) 1)))
  (SETQ VISIBILITY_TC (NTH 0 (SINGLE_ELE_LIST (EXTRACT_ATTRIBUTES ENTNAME (LIST "TC1" ) 3) 1)))
  (SETQ VISIBILITY_FDN (NTH 0 (SINGLE_ELE_LIST (EXTRACT_ATTRIBUTES ENTNAME (LIST "FOUNDATION_TYPE1" ) 3) 1)))
  (SETQ VISIBILITY_RD (NTH 0 (SINGLE_ELE_LIST (EXTRACT_ATTRIBUTES ENTNAME (LIST "RD1" ) 3) 1)))
  (SETQ VISIBILITY_DCC (NTH 0 (SINGLE_ELE_LIST (EXTRACT_ATTRIBUTES ENTNAME (LIST "DFCC_CTN_CHAINAGE1" ) 3) 1)))
  (SETQ VISIBILITY_IRC (NTH 0 (SINGLE_ELE_LIST (EXTRACT_ATTRIBUTES ENTNAME (LIST "IR_CHAINAGE1" ) 3) 1)))


  (SETQ I 0 BASE_POINT NIL ROTATION NIL TEMP_IMPLANTATION NIL TEMP_POINT_LIST NIL )
  (WHILE (< I (LENGTH ENT_LIST))
    
    (SETQ BASE_POINT (CDR (ASSOC 10 (ENTGET (NTH I ENT_LIST)))))
    (SETQ ROTATION (VLAX-GET-PROPERTY (VLAX-ENAME->VLA-OBJECT (NTH I ENT_LIST)) 'ROTATION))
    (SETQ TEMP_IMPLANTATION (ATOF (NTH 0 (SINGLE_ELE_LIST (EXTRACT_ATTRIBUTES (NTH I ENT_LIST) (LIST "IMPLANTATION1" ) 1) 1))))
    (SETQ TEMP_POINT_LIST (TRANSFORM REFERENCE_LIST BASE_POINT (-  ROTATION BASE_ROTATION)))
    (SETQ TEMP_POINT_LIST1 (TRANSFORM_ADJ REFERENCE_LIST1 BASE_POINT (-  ROTATION BASE_ROTATION) (- REFERENCE_IMPLANTATION TEMP_IMPLANTATION)))


    ;;NEWLY ADDED

    ;;;;
    
    ;(INSERT_DYNAMIC_PROPERTIES (NTH I ENT_LIST) (SINGLE_ELE_LIST AS 0) (SINGLE_ELE_LIST AS 1))
    ;(INSERT_DYNAMIC_PROPERTIES (NTH I ENT_LIST) (LIST "LEAD-LENGTH") (LIST (- (+ REFERENCE_LEAD_LENGTH REFERENCE_IMPLANTATION) TEMP_IMPLANTATION)))
    
    (INSERT_DYNAMIC_PROPERTIES (NTH I ENT_LIST) (LIST "LNM1 X" "LNM1 Y" "LCM1 X" "LCM1 Y" "LTM1 X" "LTM1 Y") (SINGLE_ELE_LIST FINAL_VALUES 1))
    
    (CHANGE_TEXT_ALIGNMENT_POINT (NTH I ENT_LIST) '("MAST_NUMBER_LINK1") (LIST (NTH 0 TEMP_POINT_LIST)))
    (CHANGE_TEXT_ALIGNMENT_POINT (NTH I ENT_LIST) '("TC1") (LIST (NTH 1 TEMP_POINT_LIST)))
    ;(CHANGE_TEXT_ALIGNMENT_POINT (NTH I ENT_LIST) '("SPAN1") (LIST (NTH 2 TEMP_POINT_LIST)))
    
    (CHANGE_TEXT_ALIGNMENT_POINT (NTH I ENT_LIST) '("FOUNDATION_TYPE1") (LIST (NTH 0 TEMP_POINT_LIST1)))
    (CHANGE_TEXT_ALIGNMENT_POINT (NTH I ENT_LIST) '("RD1") (LIST (NTH 1 TEMP_POINT_LIST1)))
    (CHANGE_TEXT_ALIGNMENT_POINT (NTH I ENT_LIST) '("DFCC_CTN_CHAINAGE1") (LIST (NTH 2 TEMP_POINT_LIST1)))
    (CHANGE_TEXT_ALIGNMENT_POINT (NTH I ENT_LIST) '("IR_CHAINAGE1") (LIST (NTH 3 TEMP_POINT_LIST1)))
      
    (CHANGE_VISIBILITY (NTH I ENT_LIST) (LIST "SPAN1" "TC1" "FOUNDATION_TYPE1" "RD1" "DFCC_CTN_CHAINAGE1" "IR_CHAINAGE1") (LIST (ITOA VISIBILITY_SPAN) (ITOA VISIBILITY_TC) (ITOA VISIBILITY_FDN) (ITOA VISIBILITY_RD) (ITOA VISIBILITY_DCC) (ITOA VISIBILITY_IRC)))
    (SETQ I (+ I 1))
  )
  (COMMAND "UCS" "P")
  )

;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;


;;;;;;;;;;;;;;;;;;;;;;;;;;;;;;;;;;;;SUPPORTING FUNCTIONS FOR MATCH BLOCKS FUNCTION;;;;;;;;;;;;;;;;;;;;;;;;;;;;;;;;;;;;;;;;;;;;;;;;;;;;;;;;;;;;;;;;;;;;;;;;;;;;;;;;


  (DEFUN TRANSFORM (LIST1 BASE_POINT ROTATION / I X Y FINAL_LIST)
  (SETQ I 0 X NIL Y NIL FINAL_LIST NIL)
  (WHILE (< I (LENGTH LIST1))
    (SETQ TEMP_POINT (POLAR BASE_POINT (+ (ANGLE (LIST 0 0 0) (NTH I LIST1)) ROTATION) (DISTANCE (LIST 0 0 0) (NTH I LIST1))))
    (SETQ FINAL_LIST (CONS TEMP_POINT FINAL_LIST))
    (SETQ I (+ I 1))
  )
  (REVERSE FINAL_LIST)
  )


  (DEFUN TRANSFORM_ADJ (LIST1 BASE_POINT ROTATION ADJUSTMENT / I X Y FINAL_LIST)
  (SETQ I 0 X NIL Y NIL FINAL_LIST NIL)
  (WHILE (< I (LENGTH LIST1))
    (SETQ TEMP_POINT (POLAR BASE_POINT (+ (ANGLE (LIST 0 0 0) (NTH I LIST1)) ROTATION) (+ (DISTANCE (LIST 0 0 0) (NTH I LIST1)) ADJUSTMENT)))
    (SETQ FINAL_LIST (CONS TEMP_POINT FINAL_LIST))
    (SETQ I (+ I 1))
  )
  (REVERSE FINAL_LIST)
  )


;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;



;;;;;;;;;;;;;;;;;;;;;;;;;;;;;;;;;;;;;;;;;;;;;;;;;;;;;;;;;;;;;PROVIDE IMPLANTATION;;;;;;;;;;;;;;;;;;;;;;;;;;;;;;;;;;;;;;;;;;;;;;;;;;;;;;;;;;;;;;;;;;;;;;;;;;;;;;;;;;;


(DEFUN C:UPDATE_SPANS_NEW (  / SSSET STARTING_MAST TRACK_CENTER ENT_LIST PROJECTTION_POINTS )
   (SETQ SSSET (SSGET))
   (SETQ STARTING_MAST (CAR(ENTSEL "N/ SELECT STARTING MAST")))
   (SETQ TRACK_CENTER (CAR(ENTSEL "N/ SELECT TRACK CENTER")))
   (COMMAND "UCS" "W")
   (SETQ ENT_LIST (FORM_SSSET SSSET))
   (SETQ ENT_LIST (EXTRACT_ENTITY_INFO ENT_LIST 1 3))
   (SETQ ENT_LIST (SORT_MASTS ENT_LIST STARTING_MAST))
   (SETQ PROJECTTION_POINTS (SINGLE_ELE_LIST (GET_PROJECTION_FROM_POINT_LIST_FINAL TRACK_CENTER ENT_LIST 1) 1))
   (UPDATE_SPAN_GPS  TRACK_CENTER  (SINGLE_ELE_LIST ENT_LIST 0) PROJECTTION_POINTS)
   (COMMAND "UCS" "P")
)


(DEFUN SORT_MASTS (ENT_LIST STARTING_MAST / I TEMP_DIST FINAL_LIST )
  (SETQ TEMP_MAST (ASSOC STARTING_MAST ENT_LIST))
  (SETQ I 0 TEMP_DIST NIL FINAL_LIST NIL)
  (WHILE (< I (LENGTH ENT_LIST))
    (SETQ TEMP_DIST (DISTANCE (NTH 1 TEMP_MAST) (NTH 1 (NTH I ENT_LIST))))
    (SETQ FINAL_LIST (CONS (APPEND (NTH I ENT_LIST) (LIST TEMP_DIST)) FINAL_LIST))
    (SETQ I (+ I 1))
  )
  (SORT_FUN (REVERSE FINAL_LIST) 0 2)
)



(DEFUN GET_PROJECTION_FROM_POINT_LIST_FINAL (LINE_ENTITY POINT_LIST FLAG  / VLA_LINE_ENTITY ST_POINT END_POINT SLOPE_ANGLE LINE_EQUATION I TEMP_ELE FINAL_LIST)
(SETQ VLA_LINE_ENTITY (VLAX-ENAME->VLA-OBJECT LINE_ENTITY))
(SETQ I 0 TEMP_ELE NIL FINAL_LIST NIL)
(WHILE (< I (LENGTH POINT_LIST))
(SETQ TEMP_ELE (VLAX-CURVE-GETCLOSESTPOINTTO LINE_ENTITY (NTH 1 (NTH I POINT_LIST)) T))
(SETQ FINAL_LIST (CONS (LIST (NTH I POINT_LIST) TEMP_ELE) FINAL_LIST))
(SETQ I (+ I 1))
)
(REVERSE FINAL_LIST)
)

(DEFUN DISTANCE_ON_CURVE_GPS ( POLYLINE_ENTITY POINT1 POINT2 / TEMP_DISTANCE1 TEMP_DISTANCE2  )
  (SETQ TEMP_DISTANCE1 (VLAX-CURVE-GETDISTATPOINT POLYLINE_ENTITY POINT1))
  (SETQ TEMP_DISTANCE2 (VLAX-CURVE-GETDISTATPOINT POLYLINE_ENTITY POINT2))
(ABS (- TEMP_DISTANCE1 TEMP_DISTANCE2))
)

(DEFUN UPDATE_SPAN_GPS (TRACK_CENTER ENT_LIST PROJECTION_POINT / I TEMP_SPAN )
  (SETQ I 0 TEMP_SPAN NIL)
  (WHILE (< I (LENGTH ENT_LIST))
    (SETQ TEMP_SPAN (RTOS (APPROXIMATE_SPAN (DISTANCE_ON_CURVE_GPS TRACK_CENTER (NTH I PROJECTION_POINT) (NTH (+ I 1) PROJECTION_POINT)) 0.75) 2 2))
    (MODIFY_ATTRIBUTES (NTH I ENT_LIST) (LIST "SPAN1" "SPAN2" "SPAN3") (N_ELE_LIST TEMP_SPAN 3))
    (SETQ I (+ I 1))
  )
)


(DEFUN GET_APPROXIMATE_VALUE ( SPAN SPAN_LIST / I TEMP_ELE LIST2 )
  (SETQ I 0)
  (SETQ TEMP_ELE NIL)
  (SETQ LIST2 NIL)
  (WHILE (< I (LENGTH SPAN_LIST))
    (SETQ TEMP_ELE (ABS (- SPAN (NTH I SPAN_LIST))))
    (SETQ LIST2 (CONS (LIST (NTH I SPAN_LIST) TEMP_ELE) LIST2))
    (SETQ I (+ I 1))
  )
(NTH 0 (NTH 0 (SORT_FUN LIST2 0 1)))
)

(DEFUN APPROXIMATE_SPAN (SPAN APPROXIMATION_VALUE / SPAN_LIST )
  (SETQ SPAN_LIST (LIST 18 22.50 27 31.50 36 40.50 45.00 49.50 54.00 58.50 63.00 67.50 72.00))
  (IF (= (VL-POSITION SPAN SPAN_LIST) NIL)
    (PROGN
      (IF (< (ABS (- SPAN (GET_APPROXIMATE_VALUE SPAN SPAN_LIST))) APPROXIMATION_VALUE)
	(SETQ SPAN (GET_APPROXIMATE_VALUE SPAN SPAN_LIST))
      )
    )
  )SPAN
)

;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;



;;;;;;;;;;;;;;;;;;;;;;;;;;;;;;;;;;;;;;;;;;;;;;;;;PROVIDE IMPLANTATION;;;;;;;;;;;;;;;;;;;;;;;;;;;;;;;;;;;;;;;;;;;;;;;;;;;;;;;;;;;;;;;;;;;;;;;;;;;;;;;;;;;;;;;;;;;;;;;;


(DEFUN C:PROVIDE_IMPLANTATION ( / ENT_LIST TRACK_CENTER IMP OS_MODE 3DOS_MODE MAST MAST_ENT REFERENCE_LEAD_LENGTH REFERENCE_IMPLANTATION INSERTION_POINT ROTATION PROJECTION_POINT FLIP FINAL_INSERTION_POINT )
   (PROMPT "N/ SELECT OBJECTS TO MOVE: ")
   (SETQ ENT_LIST (FORM_SSSET (SSGET)))
   (SETQ TRACK_CENTER (CAR(ENTSEL "N/ SELECT TRACK CENTER LINE: ")))
   (SETQ IMP (GETREAL "N/ ENTER IMPLANTATION VALUE: "))
   (SETQ OS_MODE (GETVAR "OSMODE"))
   (SETQ 3DOS_MODE (GETVAR "3DOSMODE"))
   (SETVAR "OSMODE" 0)
   (SETVAR "3DOSMODE" 0)
   (COMMAND "UCS" "W")
   (SETQ MAST_ENT (NTH 0 (SINGLE_ELE_LIST (FILTER_LIST (LIST "SINGLE_CANT_MAST" "DOUBLE_CANT_MAST" "TRIPLE_CANT_MAST" "SINGLE_CANT_DA" "DOUBLE_CANT_DA" "TRIPLE_CANT_DA" "SINGLE_CANT_UR" "DOUBLE_CANT_UR" "TRIPLE_CANT_UR" ) (EXTRACT_ENTITY_INFO2 ENT_LIST) 1) 0) ))
   (SETQ REFERENCE_LEAD_LENGTH (NTH 1 (NTH 0 (GET_DYNAMIC_PROPERTIES MAST_ENT '("LEAD-LENGTH")))))
   (SETQ REFERENCE_IMPLANTATION (ATOF (NTH 0 (SINGLE_ELE_LIST (EXTRACT_ATTRIBUTES MAST_ENT (LIST "IMPLANTATION1" ) 1) 1))))
   (SETQ MAST (VLAX-ENAME->VLA-OBJECT MAST_ENT))
   (SETQ TRACK_CENTER (VLAX-ENAME->VLA-OBJECT TRACK_CENTER))
   (SETQ INSERTION_POINT (VLAX-SAFEARRAY->LIST (VLAX-VARIANT-VALUE (VLAX-GET-PROPERTY MAST 'INSERTIONPOINT))))
   (SETQ ROTATION (VLAX-GET-PROPERTY MAST 'ROTATION))
   (SETQ PROJECTION_POINT (VLAX-CURVE-GETCLOSESTPOINTTO TRACK_CENTER INSERTION_POINT T))
   (SETQ FLIP (NTH 1 (NTH 0 (GET_DYNAMIC_PROPERTIES MAST_ENT '("STF1")))))
   (SETQ FINAL_PROJECTION_POINT NIL)
   (IF (= FLIP 0)
     (SETQ FINAL_INSERTION_POINT (POLAR PROJECTION_POINT (+ (* 1 (/ PI 2)) ROTATION) IMP))
     (SETQ FINAL_INSERTION_POINT (POLAR PROJECTION_POINT (+ (* 3 (/ PI 2)) ROTATION) IMP))
   )
   (COMMAND "MOVE" (NTH 0 ENT_LIST) (NTH 1 ENT_LIST)   "" INSERTION_POINT FINAL_INSERTION_POINT)
   (MODIFY_ATTRIBUTES MAST_ENT (LIST "IMPLANTATION1") (LIST (RTOS IMP 2 2)))
   (INSERT_DYNAMIC_PROPERTIES MAST_ENT (LIST "STL1") (LIST IMP))
   (INSERT_DYNAMIC_PROPERTIES MAST_ENT (LIST "LEAD-LENGTH") (LIST (- (+ REFERENCE_LEAD_LENGTH REFERENCE_IMPLANTATION) IMP)))
   (SETVAR "OSMODE" OS_MODE)
   (SETVAR "3DOSMODE" 3DOS_MODE)
   (COMMAND "UCS" "P")
)


;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;






;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;                                                       VIEW PORT CREATION PROGRAMS                                                                                  ;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;





(DEFUN C:CREATE_VIEWPORT ( / SHAPE CORNERS LOWEST_POINT CORNERS LOWEST_POINT ACTIVE_DOCUMENT INSERTION_POINT POINT POINT2 RECTANGLE_LENGTH RECTANGLE_WIDTH VIEWPORT )
(COMMAND "UCS" "W")
(SETQ BASE_POINTS (LIST (GETPOINT " N/ SELECT FIRST BASE POINT OF A RECTANGLE") (GETPOINT " N/ SELECT SECOND BASE POINT OF A RECTANGLE")))
(SETQ ORTHO_POINT (GETPOINT " N/ SELECT A POINT PERPENDICULAR TO BASE LINE FROM SECOND BASE POINT"))
(COMMAND "UCS" "P")
(SETQ ACTIVE_DOCUMENT (VLA-GET-ACTIVEDOCUMENT (VLAX-GET-ACAD-OBJECT)))
(VLAX-PUT-PROPERTY ACTIVE_DOCUMENT "ACTIVESPACE" ACPAPERSPACE)
(SETQ INSERTION_POINT (GETPOINT))
(SETQ LENG (DISTANCE (NTH 0 BASE_POINTS) (NTH 1 BASE_POINTS)))
(SETQ WIDTH (DISTANCE (NTH 1 BASE_POINTS) ORTHO_POINT))
;(SETQ DIAG (DISTANCE (NTH 0 BASE_POINTS) ORTHO_POINT))

(SETQ VIEWPORT (VLAX-INVOKE-METHOD (VLAX-GET-PROPERTY ACTIVE_DOCUMENT "PAPERSPACE") "ADDPVIEWPORT" (VLAX-3D-POINT INSERTION_POINT) (* 2 LENG) (* WIDTH 2)))
(VLAX-INVOKE-METHOD VIEWPORT "DISPLAY" :VLAX-TRUE)
(COMMAND "_MSPACE")
(IF (/= (GETVAR "CVPORT") (CDR (ASSOC 69 (ENTGET (VLAX-VLA-OBJECT->ENAME VIEWPORT)))))
(SETVAR "CVPORT" (CDR (ASSOC 69 (ENTGET (VLAX-VLA-OBJECT->ENAME VIEWPORT)))))
)
(ALIGNSPACE (NTH 0 BASE_POINTS) (NTH 1 BASE_POINTS) (LIST 0 0 0) (POLAR (LIST 0 0 0) 0 10))
(COMMAND "ZOOM" "W" (NTH 0 BASE_POINTS) ORTHO_POINT)
)




(DEFUN CHAINAGE_VIEWPORTS (ENTNAME ACTIVE_DOCUMENT INSERTION_POINT / MAIN_POINTS LENG WIDTH VIEWPORT )

(SETQ MAIN_POINTS (GET_BOX_POINTS_ENTITY ENTNAME))

(SETQ LENG (DISTANCE (NTH 0 MAIN_POINTS) (NTH 1 MAIN_POINTS)))
(SETQ WIDTH (DISTANCE (NTH 1 MAIN_POINTS) (NTH 2 MAIN_POINTS)))
;(SETQ DIAG (DISTANCE (NTH 0 BASE_POINTS) ORTHO_POINT))

(SETQ VIEWPORT (VLAX-INVOKE-METHOD (VLAX-GET-PROPERTY ACTIVE_DOCUMENT "PAPERSPACE") "ADDPVIEWPORT" (VLAX-3D-POINT INSERTION_POINT) (* 2 LENG) (* WIDTH 2)))
(VLAX-INVOKE-METHOD VIEWPORT "DISPLAY" :VLAX-TRUE)
(COMMAND "_MSPACE")
(IF (/= (GETVAR "CVPORT") (CDR (ASSOC 69 (ENTGET (VLAX-VLA-OBJECT->ENAME VIEWPORT)))))
(SETVAR "CVPORT" (CDR (ASSOC 69 (ENTGET (VLAX-VLA-OBJECT->ENAME VIEWPORT)))))
)
(ALIGNSPACE (NTH 0 MAIN_POINTS) (NTH 1 MAIN_POINTS) (LIST 0 0 0) (POLAR (LIST 0 0 0) 0 10))
(COMMAND "ZOOM" "W" (NTH 0 MAIN_POINTS) (NTH 2 MAIN_POINTS))
(COMMAND "_PSPACE")
)

(DEFUN GET_BOX_POINTS_ENTITY (BLOCK / BASE_POINT ROTATION RECT_POINTS SORT_Y_POINTS SORT_X_POINTS ORTHO_POINT BASE_POINTS ORTHO_POINT )
(SETQ BASE_POINT (CDR (ASSOC 10 (ENTGET BLOCK))))
(SETQ ROTATION (VLAX-GET-PROPERTY (VLAX-ENAME->VLA-OBJECT BLOCK) "ROTATION"))
(SETQ RECT_POINTS (ADD_LISTS (BUILD_LIST (FILTER_LIST (LIST "OHE-RECT-LOCATION BORDER") (Block_ename1 BLOCK) 0) (LIST 3 4)) (N_ELE_LIST 0.0 4)))
(SETQ SORT_Y_POINTS (SORT_FUN RECT_POINTS 0 1))
(SETQ SORT_X_POINTS (SORT_FUN RECT_POINTS 0 0))
(SETQ BASE_POINTS (SORT_FUN (LIST (NTH 0 SORT_Y_POINTS) (NTH 1 SORT_Y_POINTS)) 0 0))
(SETQ ORTHO_POINT (NTH 1 (SORT_FUN (LIST (NTH 2 SORT_X_POINTS) (NTH 3 SORT_X_POINTS)) 0 1)))
(SETQ BASE_POINTS (TRANSFORM BASE_POINTS BASE_POINT  ROTATION))
(SETQ ORTHO_POINT (TRANSFORM (LIST ORTHO_POINT) BASE_POINT ROTATION))
(APPEND BASE_POINTS ORTHO_POINT)
)


(DEFUN C:GET_CHAINAGE_VIEWPORTS ( / ACTIVE_DOCUMENT INSERTION_POINT I )
  (IF (= (VL-POSITION (GETVAR "CVPORT") (LIST 0 1)) NIL)
  (PROGN
  (COMMAND "UCS" "W")
  (PROMPT "N/SELECT MASTS : ")
  (SETQ MASTS (SSGET))
  (SETQ MASTS (FORM_SSSET MASTS))
  (COMMAND "UCS" "P")
  (COMMAND "_PSPACE")
  (SETQ ACTIVE_DOCUMENT (VLA-GET-ACTIVEDOCUMENT (VLAX-GET-ACAD-OBJECT)))
  (SETQ INSERTION_POINT (GETPOINT))
  (SETQ I 0)
  (WHILE (< I (LENGTH MASTS))
    (CHAINAGE_VIEWPORTS (NTH I MASTS) ACTIVE_DOCUMENT INSERTION_POINT)
    (SETQ INSERTION_POINT (LIST (+ (CAR INSERTION_POINT) 54) (CADR INSERTION_POINT) 0.0))
    (SETQ I (+ I 1))
  )
  )
  (PROGN (ALERT "THIS COMMAND IS NOT ALLOWED IN MODEL SPACE AND PAPER SPACE. ACTIVATE VIEW PORT TO RUN THIS COMMAND")
  )
  )
)
  
(DEFUN GET_BOX_POINTS ( / BLOCK BASE_POINT ROTATION RECT_POINTS SORT_Y_POINTS SORT_X_POINTS BASE_POINTS ORTHO_POINT )
(SETQ BLOCK (CAR(ENTSEL)))
(SETQ BASE_POINT (CDR (ASSOC 10 (ENTGET BLOCK))))
(SETQ ROTATION (VLAX-GET-PROPERTY (VLAX-ENAME->VLA-OBJECT BLOCK) "ROTATION"))
(SETQ RECT_POINTS (ADD_LISTS (BUILD_LIST (FILTER_LIST (LIST "OHE-RECT-LOCATION BORDER") (Block_ename1 BLOCK) 0) (LIST 3 4)) (N_ELE_LIST 0.0 4)))
(SETQ SORT_Y_POINTS (SORT_FUN RECT_POINTS 0 1))
(SETQ SORT_X_POINTS (SORT_FUN RECT_POINTS 0 0))
(SETQ BASE_POINTS (SORT_FUN (LIST (NTH 0 SORT_Y_POINTS) (NTH 1 SORT_Y_POINTS)) 0 0))
(SETQ ORTHO_POINT (NTH 1 (SORT_FUN (LIST (NTH 2 SORT_X_POINTS) (NTH 3 SORT_X_POINTS)) 0 1)))
(SETQ BASE_POINTS (TRANSFORM BASE_POINTS BASE_POINT  ROTATION))
(SETQ ORTHO_POINT (TRANSFORM (LIST ORTHO_POINT) BASE_POINT ROTATION))
(APPEND BASE_POINTS ORTHO_POINT)
)


(DEFUN TRANSFORM (LIST1 BASE_POINT ROTATION / I X Y FINAL_LIST)
  (SETQ I 0 X NIL Y NIL FINAL_LIST NIL)
  (WHILE (< I (LENGTH LIST1))
    (SETQ TEMP_POINT (POLAR BASE_POINT (+ (ANGLE (LIST 0 0 0) (NTH I LIST1)) ROTATION) (DISTANCE (LIST 0 0 0) (NTH I LIST1))))
    (SETQ FINAL_LIST (CONS TEMP_POINT FINAL_LIST))
    (SETQ I (+ I 1))
  )
(REVERSE FINAL_LIST)
)

    
(DEFUN GET_RECTANGLE_CORNERS (ENTITY  / LIST1 X )
  (SETQ LIST1 (SORT_FUN (BUILD_LIST (FILTER_LIST (LIST 10) (ENTGET ENTITY) 0) (LIST 1 2)) 0 1))
  (SETQ X
  (LIST
  (LIST (VLAX-CURVE-GETDISTATPOINT ENTITY (NTH 0 LIST1)) (NTH 0 LIST1))
  (LIST (VLAX-CURVE-GETDISTATPOINT ENTITY (NTH 1 LIST1)) (NTH 1 LIST1))
  (LIST (VLAX-CURVE-GETDISTATPOINT ENTITY (NTH 2 LIST1)) (NTH 2 LIST1))
  (LIST (VLAX-CURVE-GETDISTATPOINT ENTITY (NTH 3 LIST1)) (NTH 3 LIST1))
  )
  )
  
  (SETQ X (SORT_FUN X 0 0))
  (SETQ X (LIST (NTH 0 X) (NTH 2 X)))
  (LIST (SINGLE_ELE_LIST X 1) (NTH 0 LIST1))
)


(DEFUN GET_POINT_DIRECTION (ENTITY POINT / DIST POINT1 POINT2) 
(SETQ DIST (VLAX-CURVE-GETDISTATPOINT ENTITY POINT))
(SETQ POINT1 (VLAX-CURVE-GETPOINTATDIST ENTITY (+ DIST 10)))
(SETQ POINT2 (VLAX-CURVE-GETPOINTATDIST ENTITY (- DIST 10)))
(NTH 1 (SORT_FUN (LIST POINT1 POINT2) 0 0))
)




(DEFUN SUB_ENT_DATA_COLLECT (BLOCKENAME	FILTER_LIST
			     DFX1	DFX2	   /
			     BS_PT	ename	   SUB_ENT_LIST
			     I		TEMP_ELE   LIST2
			     J		FLAG	   LIST2
			    )
  (SETQ BS_PT (CDR (ASSOC 10 (ENTGET BLOCKENAME))))
  (if (setq
	ename (tblobjname "BLOCK" (CDR (ASSOC 2 (ENTGET BLOCKENAME))))
      )
    (reverse
      (while (setq ename (entnext ename))
	(setq SUB_ENT_LIST (cons ename SUB_ENT_LIST))
      )
    )
  )


  (SETQ I 0)
  (SETQ TEMP_ELE NIL)
  (SETQ LIST2 NIL)
  (WHILE (< I (LENGTH SUB_ENT_LIST))
    (SETQ TEMP_ELE (ENTGET (NTH I SUB_ENT_LIST)))
    (SETQ J 0)
    (SETQ FLAG 1)
    (WHILE (< J (LENGTH FILTER_LIST))
      (IF (= (VL-POSITION (NTH J FILTER_LIST) TEMP_ELE) NIL)
	(PROGN (SETQ J (LENGTH FILTER_LIST)) (SETQ FLAG 0))
      )
      (SETQ J (+ J 1))
    )
    (IF	(= FLAG 1)
      (SETQ LIST2 (CONS	(SUM_LIST1 BS_PT
				   (LIST (CDR (ASSOC DFX1 TEMP_ELE))
					 (CDR (ASSOC DFX2 TEMP_ELE))
				   )
			)
			LIST2
		  )
      )
    )
    (SETQ I (+ I 1))
  )
  (REVERSE LIST2)
)

;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;




;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;                                                               MISCLLANEOUS PROGRAMS                                                      ;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;

(DEFUN COPY_ORTHOGONAL (POLYLINE_ENTITY OBJECT PREVIOUS_POINT POINT DIST / ANGLE1 DERIVATIVE SLOPE OBJECT1 POINTS_LIST OBJECT_VLA)
(SETQ ANGLE1 (VLAX-CURVE-GETPARAMATPOINT POLYLINE_ENTITY POINT))
(SETQ DERIVATIVE (VLAX-CURVE-GETFIRSTDERIV POLYLINE_ENTITY ANGLE1))
(SETQ SLOPE (+ (/ PI 2) (ANGLE '(0 0 0) DERIVATIVE)))
(COMMAND "COPY" OBJECT "" PREVIOUS_POINT POINT)
(SETQ OBJECT1 (ENTLAST))
(SETQ POINTS_LIST (ADD_LISTS (BUILD_LIST (FILTER_LIST (LIST 10 11) (ENTGET OBJECT1) 0) (LIST 1 2)) (N_ELE_LIST 0.0 2)))
(SETQ OBJECT_VLA (VLAX-ENAME->VLA-OBJECT OBJECT1))
;(VLAX-INVOKE-METHOD (VLAX-ENAME->VLA-OBJECT OBJECT1) "ROTATE" (VLAX-3D-POINT (VLAX-CURVE-GETPOINTATDIST POLYLINE_ENTITY DIST)) (- (VLAX-GET-PROPERTY (VLAX-ENAME->VLA-OBJECT OBJECT1) "ANGLE") SLOPE))
(IF (/= (CDR(ASSOC 0 (ENTGET OBJECT1))) "XLINE")
  (COMMAND "ROTATE" OBJECT1 "" (VLAX-CURVE-GETPOINTATDIST POLYLINE_ENTITY DIST) "R" (NTH 0 POINTS_LIST) (NTH 1 POINTS_LIST) (/ (* SLOPE 180) PI))
  (COMMAND "ROTATE" OBJECT1 "" (VLAX-CURVE-GETPOINTATDIST POLYLINE_ENTITY DIST) "R" (VLAX-SAFEARRAY->LIST (VLAX-VARIANT-VALUE (VLAX-GET-PROPERTY OBJECT_VLA "BASEPOINT"))) (VLAX-SAFEARRAY->LIST (VLAX-VARIANT-VALUE (VLAX-GET-PROPERTY OBJECT_VLA "SECONDPOINT"))) (/ (* SLOPE 180) PI))
)
(LIST OBJECT1 POINT)
)



(DEFUN FIND_DIRECTION (POLYLINE_ENTITY POINT1 POINT2 / X )
  (SETQ X (- (VLAX-CURVE-GETDISTATPOINT POLYLINE_ENTITY POINT1) (VLAX-CURVE-GETDISTATPOINT POLYLINE_ENTITY POINT2)))
  (IF (= (+ X (ABS X)) 0) "NEGATIVE" "POSITIVE")
)


(DEFUN C:FIX_PEGS ( / POLYLINE_ENTITY COPY_ENTITY POINT1 POINT2 OS_MODE 3DOS_MODE DIRECTION TEMP_DISTANCE I TEMP_ELE DIST NEXT_POINT TEMP_ELE )
  (COMMAND "UCS" "W")
  (SETQ POLYLINE_ENTITY (CAR(ENTSEL "\n SELECT TRACK REFERENCE")))
  (SETQ COPY_ENTITY (CAR(ENTSEL "\n SELECT OBJECT FOR OFFSET")))
  (SETQ POINT1 (GETPOINT "\n PICK STARTING POINT ON CURVE"))
  (SETQ POINT2 (GETPOINT "\n PICK ANY POINT ON CURVE IN REQUIRED DIRECTION "))
  (SETQ OS_MODE (GETVAR "OSMODE"))
  (SETQ 3DOS_MODE (GETVAR "3DOSMODE"))
  (SETVAR "OSMODE" 0)
  (SETVAR "3DOSMODE" 0)
  (SETQ DIRECTION (FIND_DIRECTION POLYLINE_ENTITY POINT1 POINT2))
  (SETQ TEMP_DISTANCE (VLAX-CURVE-GETDISTATPOINT POLYLINE_ENTITY POINT1))
  (SETQ I 0 TEMP_ELE NIL DIST 0)
  (WHILE (/= DIST NIL)
    (SETQ DIST (GETREAL "\n ENTER DISTANCE"))
    (IF (/= DIST NIL)
    (PROGN
    (IF (= DIRECTION "POSITIVE")
      (SETQ TEMP_DISTANCE (- TEMP_DISTANCE DIST))
      (SETQ TEMP_DISTANCE (+ TEMP_DISTANCE DIST))
    )
    (SETQ NEXT_POINT (VLAX-CURVE-GETPOINTATDIST POLYLINE_ENTITY TEMP_DISTANCE))
    (SETQ TEMP_ELE (COPY_ORTHOGONAL POLYLINE_ENTITY COPY_ENTITY POINT1 NEXT_POINT TEMP_DISTANCE))
    (SETQ COPY_ENTITY (NTH 0 TEMP_ELE) POINT1 (NTH 1 TEMP_ELE))
    )
    )
  )
  (SETVAR "OSMODE" OS_MODE)
  (SETVAR "3DOSMODE" 3DOS_MODE)
  (COMMAND "UCS" "P")
)



(DEFUN OFFSETS (POLYLINE_ENTITY COPY_ENTITY POINT1 POINT2 SPAN_LIST / DIRECTION TEMP_DISTANCE I TEMP_ELE DIST DIRECTION NEXT_POINT TEMP_ELE COPY_ENTITY )
  (SETQ DIRECTION (FIND_DIRECTION POLYLINE_ENTITY POINT1 POINT2))
  (SETQ TEMP_DISTANCE (VLAX-CURVE-GETDISTATPOINT POLYLINE_ENTITY POINT1))
  (SETQ I 0 TEMP_ELE NIL DIST 0)
  (WHILE (< I (LENGTH SPAN_LIST))
    (SETQ DIST (NTH I SPAN_LIST))
    (IF (/= DIST NIL)
    (PROGN
    (IF (= DIRECTION "POSITIVE")
      (SETQ TEMP_DISTANCE (- TEMP_DISTANCE DIST))
      (SETQ TEMP_DISTANCE (+ TEMP_DISTANCE DIST))
    )
    (SETQ NEXT_POINT (VLAX-CURVE-GETPOINTATDIST POLYLINE_ENTITY TEMP_DISTANCE))
    (SETQ TEMP_ELE (COPY_ORTHOGONAL POLYLINE_ENTITY COPY_ENTITY POINT1 NEXT_POINT TEMP_DISTANCE))
    (SETQ COPY_ENTITY (NTH 0 TEMP_ELE) POINT1 (NTH 1 TEMP_ELE))
    )
    )
    (SETQ I (+ I 1))
  )
)


(DEFUN C:DISTANCE_ON_CURVE ( / POLYLINE_ENTITY POINT1 POINT2 TEMP_DISTANCE1 TEMP_DISTANCE2 I )
  (SETQ POLYLINE_ENTITY (CAR(ENTSEL "\n SELECT TRACK REFERENCE")))
  (SETQ POINT1 (TRANS (GETPOINT "\n PICK STARTING POINT ON CURVE") 1 0))
  (SETQ POINT2 (TRANS (GETPOINT "\n PICK ANY POINT ON CURVE IN REQUIRED DIRECTION ") 1 0))
  (SETQ TEMP_DISTANCE1 (VLAX-CURVE-GETDISTATPOINT POLYLINE_ENTITY POINT1))
  (SETQ TEMP_DISTANCE2 (VLAX-CURVE-GETDISTATPOINT POLYLINE_ENTITY POINT2))
(ABS (- TEMP_DISTANCE1 TEMP_DISTANCE2))
)



(DEFUN C:UPDATE_CHAINAGES_GPS (/	      SSSET
			      LOC_NO	      ST_CH
			      ENT_LIST	      BS_PT
			      ENT_INFO	      VALUES
			      VALUES1	      VALUES2
			      VALUES3	      VALUES4
			      FDN_REFERENCE   FDN_REFERENCE_X
			      FDN_REFERENCE_Y RD_REFERENCE
			      RD_REFERENCE_X  RD_REFERENCE_Y
			      TC_REFERENCE    TC_REFERENCE_X
			      TC_REFERENCE_Y  SPAN_REFERENCE_X
			      SPAN_REFERENCE_Y
			      ENT_LIST_SPAN   POINT
			      POINT1	      POINT2
			      POINT3	      ENT_LIST_SPAN
			      VISIBILITY_SPAN VISIBILITY_TC
			      VISIBILITY_FDN  VISIBILITY_RD
			      I		      LOC
			      CH	      TEMP_ELE
			      SCALE	      POINT_FDN
			      POINT_RD	      POINT_TC
			      TEMP_SPAN
			     )
  (PROMPT "\n SELECT MASTS")
  (SETQ SSSET (SSGET))
  (SETQ STARTING_MAST (CAR(ENTSEL "N/ SELECT STARTING MAST")))
  (SETQ TRACK_CENTER (CAR(ENTSEL "N/ SELECT TRACK CENTER")))
  (SETQ LOC_NO (GETSTRING "\n ENTER STARTING MAST LOCATION NUMBER :"))
  (SETQ ST_CH (GETSTRING "\n ENTER STARTING MAST CHAINAGE :"))
  (COMMAND "UCS" "W")
  (SETQ KM_NO (SUBSTR LOC_NO 1 (VL-STRING-POSITION (ASCII "/") LOC_NO)))
  (SETQ	LOC_NO (SUBSTR LOC_NO
		       (+ (VL-STRING-POSITION (ASCII "/") LOC_NO) 2)
	       )
  )
  (SETQ
    ST_CH (SUBSTR ST_CH (+ (VL-STRING-POSITION (ASCII "/") ST_CH) 2))
  )

  (SETQ	ENT_LIST (SINGLE_ELE_LIST
		   (FILTER_LIST
		     (LIST "SINGLE_CANT_MAST" "DOUBLE_CANT_MAST" "SS0" "SS1" "SS2" "SS3")
		     (EXTRACT_ENTITY_INFO2 (FORM_SSSET SSSET))
		     1
		   )
		   0
		 )
  )
  (SETQ ENT_LIST (EXTRACT_ENTITY_INFO ENT_LIST 1 3))
  (SETQ ENT_LIST (SORT_FUN ENT_LIST 1 0))
  (SETQ ENT_LIST (SORT_MASTS ENT_LIST STARTING_MAST))
  (SETQ ENT_LIST (SINGLE_ELE_LIST ENT_LIST 0))
  (SETQ BS_PT (CDR (ASSOC 10 (ENTGET (NTH 0 ENT_LIST)))))
  (SETQ ENT_INFO (YARD_STRUCTURE_INFO (NTH 0 ENT_LIST)))

  (SETQ ENT_LIST_SPAN (ATTRIBUTES_FROM_ENTITIES ENT_LIST "SPAN1" 0))
  (SETQ I 0)
  (setq dcl_id (load_dialog "DISPLAY_INFO.dcl"))
  (new_dialog "DISPLAY_INFO" dcl_id)
  (WHILE (< I (LENGTH ENT_LIST_SPAN))
    (SETQ LOC (STRCAT KM_NO "/" LOC_NO))
    (SETQ CH (STRCAT KM_NO "/" ST_CH))
    (SET_TILE "INFO"
	      (STRCAT "UPDATING LOC NO " LOC " " "OF " (ITOA I))
    )
    (SET_TILE "PERCENTAGE" (STRCAT "UPDATING CHAINAGE " CH))
    (IF	(= I (- (LENGTH ENT_LIST_SPAN) 1))
      (PROGN
	(SET_TILE "INFO"
		  (STRCAT "ALL "
			  (ITOA (+ I 1))
			  " LOCATIONS ARE UPDATED SUCESSFULLY"
		  )
	)
	(SET_TILE "PERCENTAGE" "PRESS OK TO VIEW RESULTS")
      )
    )

    (SETQ TEMP_ELE (NTH I ENT_LIST_SPAN))
    (SETQ BASE_POINT (CDR (ASSOC 10 (ENTGET (NTH 0 TEMP_ELE)))))
    (MODIFY_ATTRIBUTES
      (NTH 0 TEMP_ELE)
      (LIST "MAST_NUMBER1" "MAST_NUMBER_LINK1" "CHAINAGE1")
      (LIST LOC LOC CH)
    )


    (SETQ TEMP_SPAN (ATOF (NTH 1 TEMP_ELE)))
    (IF	(= TEMP_SPAN 0)

      (PROGN
	(IF (/= I (- (LENGTH ENT_LIST_SPAN) 1))
	  (PROGN
	    (SET_TILE "INFO"
		      (STRCAT "SPAN HAS NOT BEEN ENTERED IN LOC NO " LOC)
	    )
	    (SET_TILE "PERCENTAGE"
		      (STRCAT "PROGRAM STOPPED AT CHAINAGE "
			      CH
			      " PLEASE CHECK..."
		      )
	    )
	    (COMMAND "UCS" "P")
	  )
	)
	(SETQ I (LENGTH ENT_LIST_SPAN))
      )
    )
    (SETQ LOC_NO (ITOA (+ (ATOI LOC_NO) 2)))
    (SETQ ST_CH (RTOS (+ (ATOF ST_CH) (ATOF (NTH 1 TEMP_ELE))) 2 2))
    (SETQ I (+ I 1))
  )
  (setq ddiag (start_dialog))
  (COMMAND "UCS" "P")
)




(DEFUN C:UPDATE_LOC_NUMBERS ( / SSSET ENT_LIST I)
  (PROMPT "\n SELECT MASTS")
  (SETQ SSSET (SSGET))
    (SETQ	ENT_LIST (SINGLE_ELE_LIST
		   (FILTER_LIST
		     (LIST "SINGLE_CANT_MAST" "DOUBLE_CANT_MAST" "SS0" "SS1" "SS2" "SS3")
		     (EXTRACT_ENTITY_INFO2 (FORM_SSSET SSSET))
		     1
		   )
		   0
		 )
  )
  (SETQ I 0)
  (WHILE (< I (LENGTH ENT_LIST))
    (MODIFY_ATTRIBUTES (NTH I ENT_LIST) (LIST "MAST_NUMBER_LINK1") (LIST (NTH 1 (NTH 0 (EXTRACT_ATTRIBUTES (NTH I ENT_LIST) (LIST "MAST_NUMBER1") 1)))))
    (SETQ I (+ I 1))
  )
)




(DEFUN C:UPDATE_SPANS_GPS (  / SSSET STARTING_MAST TRACK_CENTER ENT_LIST PROJECTTION_POINTS )
   (SETQ SSSET (SSGET))
   (SETQ STARTING_MAST (CAR(ENTSEL "N/ SELECT STARTING MAST")))
   (SETQ TRACK_CENTER (CAR(ENTSEL "N/ SELECT TRACK CENTER")))
   (COMMAND "UCS" "W")
   (SETQ ENT_LIST (FORM_SSSET SSSET))
   (SETQ ENT_LIST (EXTRACT_ENTITY_INFO ENT_LIST 1 3))
   (SETQ ENT_LIST (SORT_MASTS ENT_LIST STARTING_MAST))
   (SETQ PROJECTTION_POINTS (SINGLE_ELE_LIST (GET_PROJECTION_FROM_POINT_LIST_FINAL TRACK_CENTER ENT_LIST 1) 1))
   (UPDATE_SPAN_GPS  TRACK_CENTER  (SINGLE_ELE_LIST ENT_LIST 0) PROJECTTION_POINTS)
   (COMMAND "UCS" "P")
)



(DEFUN SORT_MASTS (ENT_LIST STARTING_MAST / TEMP_MAST I TEMP_DIST FINAL_LIST )
  (SETQ TEMP_MAST (ASSOC STARTING_MAST ENT_LIST))
  (SETQ I 0 TEMP_DIST NIL FINAL_LIST NIL)
  (WHILE (< I (LENGTH ENT_LIST))
    (SETQ TEMP_DIST (DISTANCE (NTH 1 TEMP_MAST) (NTH 1 (NTH I ENT_LIST))))
    (SETQ FINAL_LIST (CONS (APPEND (NTH I ENT_LIST) (LIST TEMP_DIST)) FINAL_LIST))
    (SETQ I (+ I 1))
  )
  (SORT_FUN (REVERSE FINAL_LIST) 0 2)
)



(DEFUN GET_PROJECTION_FROM_POINT_LIST_FINAL (LINE_ENTITY POINT_LIST FLAG  / VLA_LINE_ENTITY I TEMP_ELE FINAL_LIST)
(SETQ VLA_LINE_ENTITY (VLAX-ENAME->VLA-OBJECT LINE_ENTITY))
(SETQ I 0 TEMP_ELE NIL FINAL_LIST NIL)
(WHILE (< I (LENGTH POINT_LIST))
(SETQ TEMP_ELE (VLAX-CURVE-GETCLOSESTPOINTTO LINE_ENTITY (NTH 1 (NTH I POINT_LIST)) T))
(SETQ FINAL_LIST (CONS (LIST (NTH I POINT_LIST) TEMP_ELE) FINAL_LIST))
(SETQ I (+ I 1))
)
(REVERSE FINAL_LIST)
)


(DEFUN UPDATE_SPAN_GPS (TRACK_CENTER ENT_LIST PROJECTION_POINT / I TEMP_SPAN )
  (SETQ I 0 TEMP_SPAN NIL)
  (WHILE (< I (LENGTH ENT_LIST))
    (SETQ TEMP_SPAN (RTOS (APPROXIMATE_SPAN (DISTANCE_ON_CURVE_GPS TRACK_CENTER (NTH I PROJECTION_POINT) (NTH (+ I 1) PROJECTION_POINT)) 0.5) 2 2))
    (MODIFY_ATTRIBUTES (NTH I ENT_LIST) (LIST "SPAN1" "SPAN2" "SPAN3") (N_ELE_LIST TEMP_SPAN 3))
    (SETQ I (+ I 1))
  )
)


(DEFUN GET_APPROXIMATE_VALUE ( SPAN SPAN_LIST / I TEMP_ELE LIST2 )
  (SETQ I 0)
  (SETQ TEMP_ELE NIL)
  (SETQ LIST2 NIL)
  (WHILE (< I (LENGTH SPAN_LIST))
    (SETQ TEMP_ELE (ABS (- SPAN (NTH I SPAN_LIST))))
    (SETQ LIST2 (CONS (LIST (NTH I SPAN_LIST) TEMP_ELE) LIST2))
    (SETQ I (+ I 1))
  )
(NTH 0 (NTH 0 (SORT_FUN LIST2 0 1)))
)

(DEFUN APPROXIMATE_SPAN (SPAN APPROXIMATION_VALUE / SPAN_LIST )
  (SETQ SPAN_LIST (LIST 18 22.50 27 31.50 36 40.50 45.00 49.50 54.00 58.50 63.00 67.50 72.00))
  (IF (= (VL-POSITION SPAN SPAN_LIST) NIL)
    (PROGN
      (IF (< (ABS (- SPAN (GET_APPROXIMATE_VALUE SPAN SPAN_LIST))) APPROXIMATION_VALUE)
	(SETQ SPAN (GET_APPROXIMATE_VALUE SPAN SPAN_LIST))
      )
    )
  )SPAN
)


;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;




;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;




(DEFUN C:GIVE_STAGGERING ( / SSSET ENT_LIST I FLAG1 FLAG2)

   (SETQ SSSET (SSGET))
   (SETQ ENT_LIST (FORM_SSSET SSSET))
   (SETQ ENT_LIST (EXTRACT_ENTITY_INFO ENT_LIST 1 3))
   (SETQ ENT_LIST (SORT_FUN ENT_LIST 1 0))
   (SETQ ENT_LIST (SINGLE_ELE_LIST ENT_LIST 0))
   (SETQ FLAG1 (NTH 1 (ASSOC "SGF1" (GET_DYNAMIC_PROPERTIES (NTH 0 ENT_LIST) (LIST "SGF1")))))
   (SETQ FLAG2 (IF (= FLAG1 1) 0 1))
   (SETQ I 0)
  (WHILE (< I (LENGTH ENT_LIST))
    (IF (= (REM I 2) 0) (INSERT_DYNAMIC_PROPERTIES (NTH I ENT_LIST) (LIST "SGF1") (LIST FLAG1)))
    (IF (= (REM I 2) 1) (INSERT_DYNAMIC_PROPERTIES (NTH I ENT_LIST) (LIST "SGF1") (LIST FLAG2)))
    (SETQ I (+ I 1))
  )
)



;                                                                                                                                                                  ;
;                                                            VISIBILITY MANUPULATION FUNCTIONS                                                                     ;
;                                                                                                                                                                  ;

(defun c:invis_all (/ LIST1 FLAG)
  (vl-load-com)
  (SETQ  FLAG (GETSTRING "SELECT VISIBILITY STATE 0/1 VISIBLE-->1 INVISIBLE---->0 :- "))
  (SETQ FLAG1 (GETSTRING "/N SELECT ATTRIBUTE--->S OR ENTER TAG NAME-->E"))
  (IF (= FLAG1 "S")
   (SETQ ATTR_TAG (CDR (ASSOC 2 (ENTGET (CAR (NENTSEL "SELECT ATTRIBUTE"))))))
   (SETQ ATTR_TAG (GETSTRING "/N ENTER TAGNAME : ")))
  (SETQ LIST1 (SSGET))
  (SETQ LIST1 (FORM_SSSET LIST1))
  (SETQ I 0)
  (while (< I (LENGTH LIST1))
      (CHANGE_VISIBILITY (NTH I LIST1) (LIST ATTR_TAG) (LIST FLAG))
      (SETQ  I (+ I 1)))
  (princ))



(defun c:invis (/ ent obj)
  (vl-load-com)

  (while (setq ent (car (nentsel "\nSelect Attribute: ")))
    (if (eq "ATTRIB" (cdr (assoc 0 (entget ent))))
      (vlax-put (setq obj (vlax-ename->vla-object ent)) 'invisible -1)))

  (princ))


;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;


(DEFUN C:UPDATE_CHAINAGES_PORTAL_GPS ( / SSSET LOC_NO ST_CH ENT_LIST BS_PT VALUES VALUES1 VALUES2 VALUES3 POINT POINT1 POINT2 POINT3 ENT_LIST_SPAN I LOC CH TEMP_ELE SCALE LOC_NO_DN VALUES_DN VALUES1_DN VALUES2_DN VALUES3_DN POINT_DN POINT1_DN POINT2_DN POINT3_DN LOC_DN CS_REFERENCE_X CS_REFERENCE_Y CS_REFERENCE CS_REFERENCE1 FDN_REFERENCE FDN_REFERENCE1)
  (PROMPT "\n SELECT PORTALS")
  (SETQ SSSET (SSGET))
  (SETQ SCALE (GETREAL "\nENTER SCALE : "))
  (SETQ LOC_NO (GETSTRING "\nENTER STARTING PORTAL LOCATION NUMBER TOWARDS UPLINE SIDE :"))
  (SETQ LOC_NO_DN (GETSTRING "\nENTER STARTING PORTAL LOCATION NUMBER TOWARDS DNLINE SIDE :"))
  (SETQ ST_CH (GETSTRING "\nENTER STARTING PORTAL CHAINAGE :"))(SETQ	KM_NO (SUBSTR LOC_NO 1 (VL-STRING-POSITION (ASCII "/") LOC_NO)))
  (SETQ	LOC_NO	(SUBSTR	LOC_NO (+ (VL-STRING-POSITION (ASCII "/") LOC_NO) 2)))
  (SETQ	LOC_NO_DN	(SUBSTR	LOC_NO_DN (+ (VL-STRING-POSITION (ASCII "/") LOC_NO_DN) 2)))
  (SETQ	ST_CH	(SUBSTR	ST_CH (+ (VL-STRING-POSITION (ASCII "/") ST_CH) 2)))
  (SETQ ENT_LIST (SINGLE_ELE_LIST (FILTER_LIST (LIST "PORTAL" "SS5") (EXTRACT_ENTITY_INFO2 (FORM_SSSET SSSET)) 1) 0))
  (SETQ ENT_LIST (EXTRACT_ENTITY_INFO ENT_LIST 1 3))
  (SETQ ENT_LIST (SORT_FUN ENT_LIST 1 0))
  (SETQ ENT_LIST (SINGLE_ELE_LIST ENT_LIST 0))

  
  (SETQ BS_PT (CDR (ASSOC 10 (ENTGET (NTH 0 ENT_LIST)))))

  (SETQ ENT_LIST_SPAN (GET_PORTAL_SPAN ENT_LIST))
   (setq dcl_id (load_dialog "DISPLAY_INFO.dcl"))
   (new_dialog "DISPLAY_INFO" dcl_id)
  
  (SETQ I 0)
  (WHILE (< I (LENGTH ENT_LIST_SPAN))
    (SETQ LOC (STRCAT KM_NO "/" LOC_NO))
    (SETQ LOC_DN (STRCAT KM_NO "/" LOC_NO_DN))
    (SETQ CH (STRCAT KM_NO "/" ST_CH))
    (SETQ TEMP_ELE  (NTH I ENT_LIST_SPAN))
    (SETQ BS_PT1 (CDR (ASSOC 10 (ENTGET (NTH 0 TEMP_ELE)))))
    (MODIFY_ATTRIBUTES (NTH 0 TEMP_ELE) (LIST "MAST_NUMBER1" "CHAINAGE1") (LIST LOC CH))
    (MODIFY_ATTRIBUTES (NTH 0 TEMP_ELE) (LIST "MAST_NUMBER2" "CHAINAGE2") (LIST LOC_DN CH))

     (SET_TILE "INFO" (STRCAT "UPDATING LOC NOS' "  LOC "&" LOC_DN  "OF "  (ITOA I)))
     (SET_TILE "PERCENTAGE" (STRCAT "UPDATING CHAINAGE " CH))
    (IF (= I (- (LENGTH ENT_LIST_SPAN) 1))
      (PROGN
      (SET_TILE "INFO" (STRCAT "ALL "  (ITOA I) " PORTAL LOCATIONS ARE UPDATED SUCESSFULLY"))
      (SET_TILE "PERCENTAGE" "PRESS OK TO VIEW RESULTS")
      )
    )
    (IF (/= (ATOF (NTH 1 TEMP_ELE)) 0)
    (PROGN
    (SETQ LOC_NO (ITOA (+ (ATOI LOC_NO) 2)))
    (SETQ LOC_NO_DN (ITOA (+ (ATOI LOC_NO_DN) 2)))
    (SETQ ST_CH (RTOS (+ (ATOF ST_CH) (ATOF (NTH 1 TEMP_ELE))) 2 2))

    )
    (PROGN
    (SETQ I (LENGTH ENT_LIST_SPAN))
     (IF (/= I (- (LENGTH ENT_LIST_SPAN) 1)) (PROGN (SET_TILE "INFO" (STRCAT "SPAN HAS NOT BEEN ENTERED PROPERLY OR UNEQUAL SPANS FOUND IN LOC NOS' "  LOC " & " LOC_DN  ))
     (SET_TILE "PERCENTAGE" (STRCAT "PROGRAM STOPPED AT CHAINAGE " CH " PLEASE CHECK..."))))
    )
    )
    (SETQ I (+ I 1))
    )(setq ddiag(start_dialog))
)

;;;;;;;;;;;;;;;;;;;;;;;;;;;;;;;;;;;;;;;;;;;;;;;;;;;;;;;;;;;;;;UPDATE TC FUNCTIONS;;;;;;;;;;;;;;;;;;;;;;;;;;;;;;;;;;;;;;;;;;;;;;;;;;;;;;;;;;;;;;;;;;;;;;;;;;;;;;;;;;;;;;;;;;;;;;;;;;;;;;;

(DEFUN DISTANCE2D ( PT1 PT2 / )
  (SETQ PT1 (LIST (CAR PT1) (CADR PT1)))
  (SETQ PT2 (LIST (CAR PT2) (CADR PT2)))
  (ABS (DISTANCE PT1 PT2))
)

(DEFUN C:UPDATE_IR_TC ( / BLOCKS_LIST MAST_TTC_DIR ENT_LIST DFCC_TRACK_CENTER IR_TRACK_CENTER I MAST ROTATION INSERTION_POINT PROJECTION_POINT1 PROJECTION_POINT2 FINAL_INSERTION_POINT)
;(SETQ ENT_LIST (FORM_SSSET (SSGET)))
  (SETQ BLOCKS_LIST (FORM_SSSET (SSGET "X" (LIST (CONS 0 "INSERT")))))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ ENT_LIST (SINGLE_ELE_LIST (FILTER_LIST '("DN") MAST_TTC_DIR 1) 0))
  
(SETQ DFCC_TRACK_CENTER (CAR(ENTSEL "\n SELECT DFCC TRACK CENTER:")))
(SETQ IR_TRACK_CENTER (CAR(ENTSEL "\n SELECT IR TRACK CENTER:")))
(SETQ DFCC_TRACK_CENTER (VLAX-ENAME->VLA-OBJECT DFCC_TRACK_CENTER))
(SETQ IR_TRACK_CENTER (VLAX-ENAME->VLA-OBJECT IR_TRACK_CENTER))
(SETQ I 0 MAST NIL ROTATION NIL INSERTION_POINT NIL PROJECTION_POINT1 NIL PROJECTION_POINT2 NIL FINAL_INSERTION_POINT NIL)
(WHILE (< I (LENGTH ENT_LIST))
  (SETQ MAST (VLAX-ENAME->VLA-OBJECT (NTH I ENT_LIST)))
  (SETQ ROTATION (VLAX-GET-PROPERTY MAST 'ROTATION))
  (SETQ INSERTION_POINT (VLAX-SAFEARRAY->LIST (VLAX-VARIANT-VALUE (VLAX-GET-PROPERTY MAST 'INSERTIONPOINT))))
  (SETQ PROJECTION_POINT1 (VLAX-CURVE-GETCLOSESTPOINTTO DFCC_TRACK_CENTER INSERTION_POINT T))
  (SETQ PROJECTION_POINT2 (VLAX-CURVE-GETCLOSESTPOINTTO IR_TRACK_CENTER INSERTION_POINT T))
  (IF (>= (DISTANCE2D PROJECTION_POINT1 PROJECTION_POINT2) 16)
    (SETQ FINAL_INSERTION_POINT (POLAR PROJECTION_POINT1 (+ (* 1 (/ PI 2)) ROTATION) (/ (DISTANCE2D PROJECTION_POINT1 PROJECTION_POINT2) 2)))
    (SETQ FINAL_INSERTION_POINT (POLAR PROJECTION_POINT1 (+ (* 1 (/ PI 2)) ROTATION) 8.5))
  )
  (COMMAND "INSERT" "IR_TC_BLOCK" FINAL_INSERTION_POINT "1" (* (/ 180 PI) ROTATION) )
  (MODIFY_ATTRIBUTES (ENTLAST) (LIST "DFCC_IR_TC") (LIST (STRCAT "TC=" (RTOS (DISTANCE2D PROJECTION_POINT1 PROJECTION_POINT2) 2 2))))
  (SETQ I (+ I 1))
)
)

;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;

(DEFUN FORM_SSSET (SSSET / I TEMP_ELE LIST1)
  (SETQ I 0)
  (SETQ TEMP_ELE NIL)
  (SETQ LIST1 NIL_)
  (WHILE (< I (SSLENGTH SSSET))
    (SETQ TEMP_ELE (SSNAME SSSET I))
    (SETQ LIST1 (CONS TEMP_ELE LIST1))
    (SETQ I (+ I 1))
  )
  (REVERSE LIST1)
)
;;;;;;;;;;;;;;;;;;;;;;;;;;;;;;;;;;;;;;;;;;;;;;;;;;;;;;;;;;;;;;;;;;;;








(DEFUN UPDATE_TL_GPS (MAST_LIST POLYLINE_ENTITY LIST1 LIST2 STARTING_POINT / );MAST_LIST---> (LIST ((MAST_ENTITY1 POINT1) (MAST_ENTITY2 POINT2)....)) ATTR_SET1 ATTR_SET2 MAST1_ATTR MAST2_ATTR MAST1_POINT MAST2_POINT  TL
  (IF (/= (VL-POSITION (NTH 0 LIST1) MAST_LIST) NIL)
  (PROGN
  (SETQ ATTR_SET1 (GET_ATTRIBUTES1 (NTH 0 LIST1)))
  (SETQ ATTR_SET2 (GET_ATTRIBUTES1 (NTH 0 LIST2)))
  (SETQ MAST1_ATTR (FRAME_LIST (LIST "MAST_NUMBER1" "CHAINAGE1") ATTR_SET1 1))
  (SETQ MAST2_ATTR (FRAME_LIST (LIST "MAST_NUMBER1" "CHAINAGE1") ATTR_SET2 1))
  (SETQ MAST1_POINT (VLAX-CURVE-GETCLOSESTPOINTTO POLYLINE_ENTITY (CDR(ASSOC 10 (ENTGET(NTH 0 LIST1)))) T))
  (SETQ MAST2_POINT (VLAX-CURVE-GETCLOSESTPOINTTO POLYLINE_ENTITY (CDR(ASSOC 10 (ENTGET(NTH 0 LIST2)))) T))
  (SETQ MAST_POINT_LIST (SORT_ENTITIES_ALONG_CURVE1 POLYLINE_ENTITY (LIST (LIST (NTH 0 LIST1) MAST1_POINT) (LIST (NTH 0 LIST2) MAST2_POINT)) (LIST 1 STARTING_POINT) 0 1))
  (SETQ MAST_LIST (NTH 0 (FIND_IN_BETWEEN_GPS2 MAST_POINT_LIST (BUILD_LIST (COMBINE_LIST_ELEMENTS (GET_PROJECTION_FROM_POINT_LIST_FINAL POLYLINE_ENTITY (ENTITY_DFX MAST_LIST 10 -1) 1)) (LIST 0 3)) POLYLINE_ENTITY 1 1 (NTH 0 MAST_POINT_LIST))))
  (SETQ MAST_LIST (VL-REMOVE (NTH 0 MAST_POINT_LIST) MAST_LIST))
  (SETQ MAST_LIST (VL-REMOVE (NTH 1 MAST_POINT_LIST) MAST_LIST))
  (SETQ MAST_LIST (ATTRIBUTES_FROM_ENTITIES (SINGLE_ELE_LIST (APPEND (LIST (NTH 0 MAST_POINT_LIST)) MAST_LIST) 0) "SPAN1" 0))
  (SETQ TL (RTOS (APPLY '+ (MAPCAR '(LAMBDA (X) (ATOF X)) (SINGLE_ELE_LIST MAST_LIST 1))) 2 2))
  (MODIFY_ATTRIBUTES (NTH 1 LIST1) (LIST "TENSION_LENGTH" "LOCATION_NUM" "CHAINAGE") (LIST TL (NTH 1 (ASSOC "MAST_NUMBER1" MAST2_ATTR)) (NTH 1 (ASSOC "CHAINAGE1" MAST2_ATTR))))
  (MODIFY_ATTRIBUTES (NTH 1 LIST2) (LIST "TENSION_LENGTH" "LOCATION_NUM" "CHAINAGE") (LIST TL (NTH 1 (ASSOC "MAST_NUMBER1" MAST1_ATTR)) (NTH 1 (ASSOC "CHAINAGE1" MAST1_ATTR))))
  )
  )
)



(DEFUN BREAK_MAST_WIRE_LENGTH_GPS (START_END_MAST_LIST TOTAL_MAST_LIST POLYLINE_ENTITY STARTING_POINT / I TEMP_ELE TEMP_LIST FINAL_LIST TEMP_MAST_LIST)
  (SETQ I 0 TEMP_ELE NIL TEMP_LIST NIL FINAL_LIST NIL TEMP_MAST_LIST NIL)
    (WHILE (< I (LENGTH START_END_MAST_LIST))
    (SETQ TEMP_LIST (BUILD_LIST (COMBINE_LIST_ELEMENTS (GET_PROJECTION_FROM_POINT_LIST_FINAL POLYLINE_ENTITY (ENTITY_DFX (SINGLE_ELE_LIST (NTH I START_END_MAST_LIST) 0)  10 -1) 1)) (LIST 0 3)))
    (IF (/= (VL-POSITION (NTH 0 (NTH 0 TEMP_LIST)) (SINGLE_ELE_LIST TOTAL_MAST_LIST 0)) NIL)
    (PROGN
    (SETQ TEMP_MAST_LIST (NTH 0 (FIND_IN_BETWEEN_GPS2 TEMP_LIST (BUILD_LIST (COMBINE_LIST_ELEMENTS (GET_PROJECTION_FROM_POINT_LIST_FINAL POLYLINE_ENTITY (ENTITY_DFX (SINGLE_ELE_LIST TOTAL_MAST_LIST 0)  10 -1) 1)) (LIST 0 3)) POLYLINE_ENTITY 1 1 (LIST 1 STARTING_POINT))))
    (SETQ TEMP_MAST_LIST (VL-REMOVE (NTH 0 TEMP_LIST) TEMP_MAST_LIST))
    (SETQ TEMP_MAST_LIST (VL-REMOVE (NTH 1 TEMP_LIST) TEMP_MAST_LIST))
    (SETQ TEMP_ELE (APPEND (LIST (NTH 0 TEMP_LIST)) TEMP_MAST_LIST (LIST (NTH 1 TEMP_LIST))))
    (SETQ FINAL_LIST (CONS TEMP_ELE FINAL_LIST))
    )
    )
    (SETQ I (+ I 1))
    )
(REVERSE FINAL_LIST)
)



(DEFUN FIND_IN_BETWEEN_GPS2 (LIST1 LIST2 POLYLINE_ENTITY A B STARTING_ENTITY / I FINAL_LIST TEMP_ELE1 TEMP_ELE2 J TEMP_LIST TEMP_ELE3)
  (SETQ I 1 FINAL_LIST NIL)
  (WHILE (< I (LENGTH LIST1))
    (SETQ TEMP_ELE1 (NTH A (NTH (- I 1) LIST1)) TEMP_ELE2 (NTH A (NTH I LIST1)))
    (SETQ J 0 TEMP_LIST NIL)
    (WHILE (< J (LENGTH LIST2))
      (SETQ TEMP_ELE3 (NTH B (NTH J LIST2)))
      
        (SETQ TEMP_DISTANCE1 (ABS (VLAX-CURVE-GETDISTATPOINT POLYLINE_ENTITY TEMP_ELE1)))
        (SETQ TEMP_DISTANCE2 (ABS (VLAX-CURVE-GETDISTATPOINT POLYLINE_ENTITY TEMP_ELE2)))
        (SETQ TEMP_DISTANCE3 (ABS (VLAX-CURVE-GETDISTATPOINT POLYLINE_ENTITY TEMP_ELE3)))
      
      (IF (OR (AND (> TEMP_DISTANCE3 TEMP_DISTANCE1) (< TEMP_DISTANCE3 TEMP_DISTANCE2))
	  (AND (< TEMP_DISTANCE3 TEMP_DISTANCE1) (> TEMP_DISTANCE3 TEMP_DISTANCE2)))
      (SETQ TEMP_LIST (CONS (NTH J LIST2) TEMP_LIST)))
      
      (SETQ J (+ J 1))
    )
    (SETQ FINAL_LIST (CONS (SORT_ENTITIES_ALONG_CURVE1 POLYLINE_ENTITY TEMP_LIST STARTING_ENTITY 0 1) FINAL_LIST))
    (SETQ I (+ I 1))
  )
  (REVERSE FINAL_LIST)
)



(DEFUN DATA_TO_STRUCTURE_MAP_SECTIONING (LIST1 LIST2 K Q  / I TEMP_ELE TEMP_ELE1 LIST3)
(SETQ I 0)
(SETQ TEMP_ELE NIL)
(SETQ TEMP_ELE1 NIL)
(SETQ LIST3 NIL)
(WHILE (< I (LENGTH LIST1))
  (SETQ TEMP_ELE1 (MAP_NEAREST1 LIST2 (NTH K (NTH I LIST1)) Q ))
  (SETQ TEMP_ELE (APPEND (LIST (NTH 0 (NTH I LIST1))) TEMP_ELE1 ))
  (SETQ LIST3 (CONS TEMP_ELE LIST3))
  ;(SETQ LIST2 (VL-REMOVE TEMP_ELE1 LIST2))
  (SETQ I (+ I 1))
  )
LIST3
)

(DEFUN C:UPDATE_TENSION_LENGTHS_GPS ( / I WPT1 WPT2 WPT3 WPT4 TRACK_ENTITY_UPTRACK BLOCKS_LIST MAST_UP MAST_DN BLOCK_NAME_LIST ACC_LIST OLC_LIST TL_LIST MAST_TTC ANCHOR_ENTITIES ANCHOR_START ANCHOR_END MAIN_LIST )
  ;(SETQ WPT1 (GETPOINT "\n ENTER 1ST POINT OF POLYGON"))
  ;(SETQ WPT2 (GETPOINT "\n ENTER 2ND POINT OF POLYGON"))
  ;(SETQ WPT3 (GETPOINT "\n ENTER 3RD POINT OF POLYGON"))
  ;(SETQ WPT4 (GETPOINT "\n ENTER 4TH POINT OF POLYGON"))
  ;(SETQ BLOCKS_LIST (FORM_SSSET (SSGET "WP" (LIST WPT1 WPT2 WPT3 WPT4) (LIST (CONS 0 "INSERT")))))
  (SETQ BLOCKS_LIST (FORM_SSSET (SSGET "X" (LIST (CONS 0 "INSERT")))))
  (SETQ TRACK_ENTITY_UPTRACK (CAR(ENTSEL "\nSELECT TRACK ALIGNMENT FOR UP TRACK (DN LINE):")))
  (SETQ TRACK_ENTITY_DNTRACK (CAR(ENTSEL "\nSELECT TRACK ALIGNMENT FOR DN TRACK (UP LINE):")))
  (SETQ STARTING_POINT (GETPOINT "\nENTER STARTING POINT FOR UP TRACK (DN LINE):"))
  (SETQ STARTING_POINT_DN (GETPOINT "\nENTER STARTING POINT FOR DN TRACK (UP LINE):"))

  
  

  
  (SETQ BLOCK_NAME_LIST (EXTRACT_ENTITY_INFO2 BLOCKS_LIST))
  (SETQ ACC_LIST (FILTER_LIST (LIST "ACC") BLOCK_NAME_LIST 1))
  (SETQ OLC_LIST (FILTER_LIST (LIST "OLC") BLOCK_NAME_LIST 1))
  (SETQ TL_LIST (FILTER_LIST (LIST "TENSION_LENGTH") BLOCK_NAME_LIST 1))
  (SETQ ACC_LIST (BUILD_LIST (ENTITY_DFX (SINGLE_ELE_LIST ACC_LIST 0) 10 -1) (LIST 0 1)))
  (SETQ OLC_LIST (BUILD_LIST (ENTITY_DFX (SINGLE_ELE_LIST OLC_LIST 0) 10 -1) (LIST 0 1)))
  (SETQ TL_LIST  (BUILD_LIST (ENTITY_DFX (SINGLE_ELE_LIST TL_LIST 0)  10 -1) (LIST 0 1)))
  ;(COMMAND "BURST" (ENTLAST))
  (SETQ MAST_TTC (YARD_DATA_COLLECT_GPS BLOCKS_LIST '("SINGLE_CANT_MAST" "DOUBLE_CANT_MAST" "TRIPLE_CANT_MAST" "TTC" "SS0" "SS1" "SS2" "SS3" "SS4") 1 3))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  ;(SETQ ANCHOR_LIST (YARD_DATA_COLLECT WPT1 WPT2 '("ANCHOR") 1 3))
 (SETQ ANCHOR_ENTITIES (YARD_DATA_COLLECT_GPS BLOCKS_LIST '("ANCHOR") 1 5))
 (SETQ BTB_ANCHOR_ENTITIES (YARD_DATA_COLLECT_GPS BLOCKS_LIST '("BTB_ANC") 1 3))
 (SETQ ANCHOR_START (FILTER_LIST '("START") ANCHOR_ENTITIES 1))
 (SETQ ANCHOR_END (FILTER_LIST '("END") ANCHOR_ENTITIES 1))
  
 (SETQ MAST_UP (FILTER_LIST '("UP") MAST_TTC_DIR 1))
 (SETQ MAST_DN (FILTER_LIST '("DN") MAST_TTC_DIR 1))
  
 (SETQ ANCHOR_START  (BUILD_LIST (ENTITY_DFX (SINGLE_ELE_LIST ANCHOR_START 0)  10 -1) (LIST 0 1)))
 (SETQ ANCHOR_END  (BUILD_LIST (ENTITY_DFX (SINGLE_ELE_LIST ANCHOR_END 0)  10 -1) (LIST 0 1)))

  
  (IF (/= ANCHOR_START NIL) (SETQ ANCHOR_START_STRUCTURE_MAP_DATA (DATA_TO_STRUCTURE_MAP_SECTIONING ANCHOR_START MAST_TTC 1 1)) (SETQ ANCHOR_START NIL))
  (IF (/= ANCHOR_END NIL) (SETQ ANCHOR_END_STRUCTURE_MAP_DATA (DATA_TO_STRUCTURE_MAP_SECTIONING ANCHOR_END MAST_TTC 1 1)) (SETQ ANCHOR_END NIL))
  
  (IF (/= ACC_LIST NIL) (SETQ ACC_STRUCTURE_MAP_DATA (DATA_TO_STRUCTURE_MAP_SECTIONING ACC_LIST MAST_TTC 1 1)) (SETQ ACC_STRUCTURE_MAP_DATA NIL))
  (IF (/= OLC_LIST NIL) (SETQ OLC_STRUCTURE_MAP_DATA (DATA_TO_STRUCTURE_MAP_SECTIONING OLC_LIST MAST_TTC 1 1)) (SETQ OLC_STRUCTURE_MAP_DATA NIL))
  (IF (/= TL_LIST NIL) (SETQ TL_STRUCTURE_MAP_DATA (DATA_TO_STRUCTURE_MAP_SECTIONING TL_LIST MAST_TTC 1 1)) (SETQ TL_STRUCTURE_MAP_DATA NIL))
 (SETQ MAIN_LIST (MAP_TENSION_LENGTHS ANCHOR_START_STRUCTURE_MAP_DATA ANCHOR_END_STRUCTURE_MAP_DATA TL_STRUCTURE_MAP_DATA))

 (SETQ I 0)
 (WHILE (< I (LENGTH MAIN_LIST))
  (UPDATE_TL_GPS (SINGLE_ELE_LIST MAST_UP 0) TRACK_ENTITY_UPTRACK (NTH 0 (NTH I MAIN_LIST)) (NTH 1 (NTH I MAIN_LIST)) STARTING_POINT)
  (UPDATE_TL_GPS (SINGLE_ELE_LIST MAST_DN 0) TRACK_ENTITY_UPTRACK (NTH 0 (NTH I MAIN_LIST)) (NTH 1 (NTH I MAIN_LIST)) STARTING_POINT)
  (SETQ I (+ I 1))
 )
  
 (SETQ MAST_UP  (ADD_LISTS (BUILD_LIST (ENTITY_DFX (SINGLE_ELE_LIST MAST_UP 0)  10 -1) (LIST 0 1)) (N_ELE_LIST "UP" (LENGTH MAST_UP))))
 (SETQ MAST_DN  (ADD_LISTS (BUILD_LIST (ENTITY_DFX (SINGLE_ELE_LIST MAST_DN 0)  10 -1) (LIST 0 1)) (N_ELE_LIST "DN" (LENGTH MAST_DN))))

  (IF (/= BTB_ANCHOR_ENTITIES NIL) (SETQ BTB_ANCHOR_STRUCTURE_MAP_DATA_TOTAL (DATA_TO_STRUCTURE_MAP_SECTIONING BTB_ANCHOR_ENTITIES (APPEND MAST_UP MAST_DN) 1 1)) (SETQ BTB_ANCHOR_ENTITIES NIL))
  (SETQ BTB_ANCHOR_STRUCTURE_MAP_DATA_TOTAL (BUILD_LIST (SORT_ENTITIES_ALONG_CURVE1 TRACK_ENTITY_UPTRACK (ADD_LISTS BTB_ANCHOR_STRUCTURE_MAP_DATA_TOTAL (SINGLE_ELE_LIST (ENTITY_DFX (SINGLE_ELE_LIST BTB_ANCHOR_STRUCTURE_MAP_DATA_TOTAL 0)  10 -1) 1)) (LIST 1 STARTING_POINT) 1 1) (LIST 0 1 3)))
  (SETQ BTB_ANCHOR_STRUCTURE_MAP_DATA_TOTAL (ADD_LISTS BTB_ANCHOR_STRUCTURE_MAP_DATA_TOTAL (SINGLE_ELE_LIST (ATTRIBUTES_FROM_ENTITIES (SINGLE_ELE_LIST BTB_ANCHOR_STRUCTURE_MAP_DATA_TOTAL 0) "ANCHOR_TYPE1" 1) 1)))
  (UPDATE_BTB_TL_GPS (SINGLE_ELE_LIST MAST_UP 0) TRACK_ENTITY_UPTRACK (FILTER_LIST (LIST "FA")  (FILTER_LIST (LIST "UP") BTB_ANCHOR_STRUCTURE_MAP_DATA_TOTAL 2) 3) TL_STRUCTURE_MAP_DATA STARTING_POINT)
  (UPDATE_BTB_TL_GPS (SINGLE_ELE_LIST MAST_DN 0) TRACK_ENTITY_UPTRACK (FILTER_LIST (LIST "FA")  (FILTER_LIST (LIST "DN") BTB_ANCHOR_STRUCTURE_MAP_DATA_TOTAL 2) 3) TL_STRUCTURE_MAP_DATA STARTING_POINT)
  (UPDATE_BTB_TL_GPS (SINGLE_ELE_LIST MAST_UP 0) TRACK_ENTITY_UPTRACK (FILTER_LIST (LIST "AEWA")  (FILTER_LIST (LIST "UP") BTB_ANCHOR_STRUCTURE_MAP_DATA_TOTAL 2) 3) TL_STRUCTURE_MAP_DATA STARTING_POINT)
  (UPDATE_BTB_TL_GPS (SINGLE_ELE_LIST MAST_DN 0) TRACK_ENTITY_UPTRACK (FILTER_LIST (LIST "AEWA")  (FILTER_LIST (LIST "DN") BTB_ANCHOR_STRUCTURE_MAP_DATA_TOTAL 2) 3) TL_STRUCTURE_MAP_DATA STARTING_POINT)


 
 (SETQ START_END_MAST_LIST_FOR_ACC (ADD_LISTS1 (BUILD_LIST (ENTITY_DFX (SINGLE_ELE_LIST (SINGLE_ELE_LIST MAIN_LIST 0) 0)  10 -1) (LIST 0 1))  (BUILD_LIST (ENTITY_DFX (SINGLE_ELE_LIST (SINGLE_ELE_LIST MAIN_LIST 1) 0)  10 -1) (LIST 0 1))))
 (SETQ MAST_LIST_FOR_ACC_UP (BREAK_MAST_WIRE_LENGTH_GPS START_END_MAST_LIST_FOR_ACC (BUILD_LIST (ENTITY_DFX (SINGLE_ELE_LIST MAST_UP 0) 10 -1) (LIST 0 1)) TRACK_ENTITY_UPTRACK STARTING_POINT))
 (SETQ MAST_LIST_FOR_ACC_DN (BREAK_MAST_WIRE_LENGTH_GPS START_END_MAST_LIST_FOR_ACC (BUILD_LIST (ENTITY_DFX (SINGLE_ELE_LIST MAST_DN 0) 10 -1) (LIST 0 1)) TRACK_ENTITY_UPTRACK STARTING_POINT))
 (UPDATE_ACC_LIST MAST_LIST_FOR_ACC_UP ACC_STRUCTURE_MAP_DATA)
 (UPDATE_ACC_LIST MAST_LIST_FOR_ACC_DN ACC_STRUCTURE_MAP_DATA)
 (UPDATE_OLC_CHAINAGE OLC_STRUCTURE_MAP_DATA)

)







(DEFUN FIND_IN_BETWEEN (LIST1 LIST2 A B C / I FINAL_LIST TEMP_ELE1 TEMP_ELE2 J TEMP_LIST TEMP_ELE3)
  (SETQ I 1 FINAL_LIST NIL)
  (WHILE (< I (LENGTH LIST1))
    (SETQ TEMP_ELE1 (NTH A (NTH (- I 1) LIST1)) TEMP_ELE2 (NTH A (NTH I LIST1)))
    (SETQ J 0 TEMP_LIST NIL)
    (WHILE (< J (LENGTH LIST2))
      (SETQ TEMP_ELE3 (NTH B (NTH C (NTH J LIST2))))
      (IF (AND (> TEMP_ELE3 TEMP_ELE1) (< TEMP_ELE3 TEMP_ELE2)) (SETQ TEMP_LIST (CONS (NTH J LIST2) TEMP_LIST)))
      (SETQ J (+ J 1))
    )
    (SETQ FINAL_LIST (CONS TEMP_LIST FINAL_LIST))
    (SETQ I (+ I 1))
  )
  (REVERSE FINAL_LIST)
)



(DEFUN UPDATE_BTB_TL_GPS (MAST_LIST  POLYLINE_ENTITY BTB_ANCHOR_STRUCTURE_MAP_DATA TL_STRUCTURE_MAP_DATA STARTING_POINT / I TEMP_MAST1 TEMP_TL_LIST1 TL_ST1 TEMP_ELE1 TEMP_MAST2 TEMP_TL_LIST2 TL_ST2 TEMP_ELE2)
  (SETQ I 0 TEMP_MAST1 NIL TEMP_TL_LIST1 NIL TL_ST1 NIL TEMP_ELE1 NIL TEMP_MAST2 NIL TEMP_TL_LIST2 NIL TL_ST2 NIL TEMP_ELE2 NIL)
  (WHILE (< I (LENGTH BTB_ANCHOR_STRUCTURE_MAP_DATA))
    (SETQ TEMP_MAST1 (NTH 1 (NTH I BTB_ANCHOR_STRUCTURE_MAP_DATA)))
    (SETQ TEMP_TL_LIST1 (SINGLE_ELE_LIST (FILTER_LIST (LIST TEMP_MAST1) TL_STRUCTURE_MAP_DATA 1) 0))
    (IF (= (NTH 1 (NTH 0 (GET_DYNAMIC_PROPERTIES (NTH 0 TEMP_TL_LIST1) (LIST "TLF2")))) 1) (SETQ TL_ST1 (NTH 0 TEMP_TL_LIST1)) (SETQ TL_ST1 (NTH 1 TEMP_TL_LIST1)))
    (SETQ TEMP_ELE1 (LIST (NTH 1 (NTH I BTB_ANCHOR_STRUCTURE_MAP_DATA)) TL_ST1))
    (IF (/= (NTH (+ I 1) BTB_ANCHOR_STRUCTURE_MAP_DATA) NIL)
    (PROGN
    (SETQ TEMP_MAST2 (NTH 1 (NTH (+ I 1) BTB_ANCHOR_STRUCTURE_MAP_DATA)))
    (SETQ TEMP_TL_LIST2 (SINGLE_ELE_LIST (FILTER_LIST (LIST TEMP_MAST2) TL_STRUCTURE_MAP_DATA 1) 0))
    (IF (= (NTH 1 (NTH 0 (GET_DYNAMIC_PROPERTIES (NTH 0 TEMP_TL_LIST2) (LIST "TLF2")))) 0) (SETQ TL_ST2 (NTH 0 TEMP_TL_LIST2)) (SETQ TL_ST2 (NTH 1 TEMP_TL_LIST2)))
    (SETQ TEMP_ELE2 (LIST (NTH 1 (NTH (+ I 1) BTB_ANCHOR_STRUCTURE_MAP_DATA)) TL_ST2))
    (UPDATE_TL_GPS MAST_LIST POLYLINE_ENTITY TEMP_ELE1 TEMP_ELE2 STARTING_POINT)
    ))
    (SETQ I (+ I 1))
  )
)




(DEFUN UPDATE_OLC_CHAINAGE (OLC_LIST / I TEMP_OLC TEMP_MAST TEMP_CHAINAGE )
  (SETQ I 0 TEMP_OLC NIL TEMP_MAST NIL TEMP_CHAINAGE NIL)
  (WHILE (< I (LENGTH OLC_LIST))
    (SETQ TEMP_OLC (NTH 0 (NTH I OLC_LIST)))
    (SETQ TEMP_MAST (NTH 1 (NTH I OLC_LIST)))
    (SETQ TEMP_CHAINAGE (NTH 1 (ASSOC "CHAINAGE1" (GET_ATTRIBUTES1 TEMP_MAST))))
    (MODIFY_ATTRIBUTES TEMP_OLC (LIST "CHAINAGE") (LIST (STRCAT "CH: " TEMP_CHAINAGE)))
    (IF (= (NTH 1 (NTH 0 (GET_DYNAMIC_PROPERTIES TEMP_MAST (LIST "STF1")))) 0)
      (MODIFY_ATTRIBUTES TEMP_OLC (LIST "TRACK") (LIST "FOR DN MAIN"))
      (MODIFY_ATTRIBUTES TEMP_OLC (LIST "TRACK") (LIST "FOR UP MAIN"))
    )
    (SETQ I (+ I 1))
  )
)

(DEFUN MAP_TENSION_LENGTHS ( ANCHOR_START_STRUCTURE_MAP_DATA ANCHOR_END_STRUCTURE_MAP_DATA TL_STRUCTURE_MAP_DATA / I TEMP_WIRE_RUN TEMP_ELE TEMP_TL1 TEMP_TL2 TEMP_LIST FINAL_LIST )
  (SETQ I 0 TEMP_WIRE_RUN NIL TEMP_ELE NIL TEMP_TL1 NIL TEMP_TL2 NIL TEMP_LIST NIL FINAL_LIST NIL)
  (SETQ ANCHOR_START_STRUCTURE_MAP_DATA (BUILD_LIST (ADD_LISTS ANCHOR_START_STRUCTURE_MAP_DATA (SINGLE_ELE_LIST (ATTRIBUTES_FROM_ENTITIES (SINGLE_ELE_LIST ANCHOR_START_STRUCTURE_MAP_DATA 0) "WIRE_RUN1" 0) 1)) (LIST 3 0 1)))
  (SETQ ANCHOR_END_STRUCTURE_MAP_DATA (BUILD_LIST (ADD_LISTS ANCHOR_END_STRUCTURE_MAP_DATA (SINGLE_ELE_LIST (ATTRIBUTES_FROM_ENTITIES (SINGLE_ELE_LIST ANCHOR_END_STRUCTURE_MAP_DATA 0) "WIRE_RUN1" 0) 1)) (LIST 3 0 1)))
  (SETQ TL_STRUCTURE_MAP_DATA (BUILD_LIST TL_STRUCTURE_MAP_DATA (LIST 1 0)))
  (WHILE (< I (LENGTH ANCHOR_START_STRUCTURE_MAP_DATA))
    (SETQ TEMP_ELE (ASSOC (NTH 0 (NTH I ANCHOR_START_STRUCTURE_MAP_DATA)) ANCHOR_END_STRUCTURE_MAP_DATA))
    (IF (/= TEMP_ELE NIL)
     (PROGN
      (SETQ TEMP_TL1 (ASSOC (NTH 2 (NTH I ANCHOR_START_STRUCTURE_MAP_DATA)) TL_STRUCTURE_MAP_DATA))
      (SETQ TEMP_TL2 (ASSOC (NTH 2 TEMP_ELE) TL_STRUCTURE_MAP_DATA))
      (IF (AND (/= TEMP_TL1 NIL) (/= TEMP_TL2 NIL))
      (PROGN
      (SETQ TEMP_LIST (LIST (LIST (NTH 2 (NTH I ANCHOR_START_STRUCTURE_MAP_DATA)) (NTH 1 TEMP_TL1)) (LIST (NTH 2 TEMP_ELE) (NTH 1 TEMP_TL2))))
      (SETQ FINAL_LIST (CONS TEMP_LIST FINAL_LIST))
      )
      )
     )
    )
   (SETQ I (+ I 1))
  )
 (REVERSE FINAL_LIST)
)






(DEFUN UPDATE_ACC_LIST ( MAST_LIST ACC_STRUCTURE_MAP_DATA / I TEMP_ACC_MAST_DATA TEMP_POSITION TEMP_LEFT_COUNT TEMP_RIGHT_COUNT TEMP_LEFT_LENGTH TEMP_RIGHT_LENGTH)
  (SETQ I 0 TEMP_ACC_MAST_DATA NIL TEMP_POSITION NIL TEMP_LEFT_COUNT NIL TEMP_RIGHT_COUNT NIL TEMP_LEFT_LENGTH NIL TEMP_RIGHT_LENGTH NIL TEMP_LEFT_MAST_DATA NIL TEMP_RIGHT_MAST_DATA NIL)
  (WHILE (< I (LENGTH MAST_LIST))
    (IF (/= (FILTER_LIST (SINGLE_ELE_LIST (NTH I MAST_LIST)  0) ACC_STRUCTURE_MAP_DATA 1) NIL)
    (PROGN
    (SETQ TEMP_ACC_MAST_DATA (NTH 0 (FILTER_LIST (SINGLE_ELE_LIST (NTH I MAST_LIST)  0) ACC_STRUCTURE_MAP_DATA 1)))
    (SETQ TEMP_POSITION (VL-POSITION (NTH 1 TEMP_ACC_MAST_DATA) (SINGLE_ELE_LIST (NTH I MAST_LIST)  0)))
    (SETQ TEMP_LEFT_COUNT (RTOS TEMP_POSITION 2 0))
    (SETQ TEMP_RIGHT_COUNT (RTOS (- (- (LENGTH (NTH I MAST_LIST)) TEMP_POSITION) 1) 2 0))
    (SETQ TEMP_LEFT_MAST_DATA (CDR (MEMBER (NTH 1 TEMP_ACC_MAST_DATA) (REVERSE (SINGLE_ELE_LIST (NTH I MAST_LIST) 0)))))
    (SETQ TEMP_RIGHT_MAST_DATA (CDR (REVERSE (MEMBER (NTH 1 TEMP_ACC_MAST_DATA) (SINGLE_ELE_LIST (NTH I MAST_LIST) 0)))))
    (SETQ TEMP_LEFT_MAST_DATA (ATTRIBUTES_FROM_ENTITIES (SINGLE_ELE_LIST TEMP_LEFT_MAST_DATA 0) "SPAN1" 0))
    (SETQ TEMP_RIGHT_MAST_DATA (ATTRIBUTES_FROM_ENTITIES (SINGLE_ELE_LIST TEMP_RIGHT_MAST_DATA 0) "SPAN1" 0))
    (SETQ TEMP_LEFT_MAST_DATA1 (RTOS (APPLY '+ (MAPCAR '(LAMBDA (X) (ATOF X)) (SINGLE_ELE_LIST TEMP_LEFT_MAST_DATA 1))) 2 2))
    (SETQ TEMP_RIGHT_MAST_DATA1 (RTOS (APPLY '+ (MAPCAR '(LAMBDA (X) (ATOF X)) (SINGLE_ELE_LIST TEMP_RIGHT_MAST_DATA 1))) 2 2))
    (MODIFY_ATTRIBUTES (NTH 0 TEMP_ACC_MAST_DATA) (LIST "MAST_COUNT1" "MAST_COUNT2" "TENSION_LENGTH1" "TENSION_LENGTH2") (LIST TEMP_LEFT_COUNT TEMP_RIGHT_COUNT TEMP_LEFT_MAST_DATA1 TEMP_RIGHT_MAST_DATA1))
    )
    )
    (SETQ I (+ I 1))
  )
)




(DEFUN C:PRINT_OBSTRUCTIONS_GPS ( / )
  (SETQ POINT1 (GETPOINT "\n PICK STARTING POINT ON CURVE"))
  (SETQ POINT2 (GETPOINT "\n PICK ANY POINT ON CURVE IN REQUIRED DIRECTION "))
  (SETQ OS_MODE (GETVAR "OSMODE"))
  (SETQ 3DOS_MODE (GETVAR "3DOSMODE"))
  (SETVAR "OSMODE" 0)
  (SETVAR "3DOSMODE" 0)
  (SETQ START_CELL (GETSTRING "\N ENTER STARTING CELL"))
  (SETQ END_CELL (GETSTRING "\N ENTER ENDING CELL"))
  (SETQ BLOCKS_LIST (FORM_SSSET (SSGET "X" (LIST (CONS 0 "INSERT")))))
  (SETQ BLOCK_NAME_LIST (EXTRACT_ENTITY_INFO2 BLOCKS_LIST))
  (SETQ KM_STONE_LIST (FILTER_LIST (LIST "DFCC_KM_NEW") BLOCK_NAME_LIST 1))
  (SETQ KM_STONE_LIST (SORT_FUN (ENTITY_DFX (SINGLE_ELE_LIST KM_STONE_LIST 0) 10 -1) 1 0))

  (SETQ KM_START (CAR(ENTSEL "\nSELECT STARTING KM :")))

  (SETQ TRACK_ENTITY_UPTRACK (CAR(ENTSEL "\nSELECT TRACK ALIGNMENT FOR DNLINE:")))

  (SETQ TRACK_ENTITY_DNTRACK (CAR(ENTSEL "\nSELECT TRACK ALIGNMENT FOR UPLINE:")))

  (SETQ TRACK_ENTITY_CENTERLINE (CAR(ENTSEL "\nSELECT CENTER LINE BETWEEN DNLINE AND UPLINE :")))

  (SETQ DIRECTION (FIND_DIRECTION TRACK_ENTITY_UPTRACK POINT1 POINT2))

  (SETQ KM_STONE_COORDINATES (COMBINE_LIST_ELEMENTS (GET_PROJECTION_FROM_POINT_LIST_FINAL TRACK_ENTITY_UPTRACK (BUILD_LIST KM_STONE_LIST (LIST 0 1)) 1)))

  (SETQ KM_STONE_COORDINATES (BUILD_LIST (SORT_ENTITIES_ALONG_CURVE TRACK_ENTITY_UPTRACK KM_STONE_COORDINATES (ASSOC KM_START KM_STONE_COORDINATES) 2 2) (LIST 0 2)))

  (SETQ KM_STONE_COORDINATES (GET_KM_STONE_COORDINATES KM_STONE_COORDINATES))

  (SETQ KMLIST (getCellsrow/column "Sheet1" (STRCAT (COLUMN+N START_CELL 0) ":" (COLUMN+N END_CELL 0))))
  (SETQ CHAINAGE_LIST (getCellsrow/column "Sheet1" (STRCAT (COLUMN+N START_CELL 1) ":" (COLUMN+N END_CELL 1))))
  (SETQ OBSTRUCTION_LIST (getCellsrow/column "Sheet1" (STRCAT (COLUMN+N START_CELL 2) ":" (COLUMN+N END_CELL 2))))
  (SETQ DIRECTION_LIST (getCellsrow/column "Sheet1" (STRCAT (COLUMN+N START_CELL 3) ":" (COLUMN+N END_CELL 3))))
  (SETQ WIDTH_LIST (getCellsrow/column "Sheet1" (STRCAT (COLUMN+N START_CELL 4) ":" (COLUMN+N END_CELL 4))))
  (SETQ NUMBER_LIST (getCellsrow/column "Sheet1" (STRCAT (COLUMN+N START_CELL 5) ":" (COLUMN+N END_CELL 5))))
  (SETQ CONT_CHAINAGE_LIST (getCellsrow/column "Sheet1" (STRCAT (COLUMN+N START_CELL 6) ":" (COLUMN+N END_CELL 6))))
  (SETQ TOTAL_LIST (ADD_LISTS (ADD_LISTS (ADD_LISTS (ADD_LISTS (ADD_LISTS1 KMLIST CHAINAGE_LIST) (ADD_LISTS1 OBSTRUCTION_LIST DIRECTION_LIST)) WIDTH_LIST) NUMBER_LIST) CONT_CHAINAGE_LIST))
  (INSERT_OBSTRUCTIONS_GPS TOTAL_LIST KM_STONE_COORDINATES TRACK_ENTITY_UPTRACK TRACK_ENTITY_DNTRACK TRACK_ENTITY_CENTERLINE DIRECTION)
  (COMMAND "REGEN")
)
  

(DEFUN CHANGE_ATTRIBUTE_ROTATION1 (ENTNAME ATTRIBUTE_NAME TEMP_ROTATION / ENT_OBJECT SAFEARRAY_SET I LIST1)
  (SETQ SAFEARRAY_SET NIL)
  (SETQ ENT_OBJECT ENTNAME)
  (SETQ ENT_OBJECT (VLAX-ENAME->VLA-OBJECT ENT_OBJECT))
  (IF (= (VLAX-GET-PROPERTY ENT_OBJECT "HASATTRIBUTES") :VLAX-TRUE)
  (PROGN
  (SETQ	SAFEARRAY_SET
	 (VLAX-SAFEARRAY->LIST
	   (VLAX-VARIANT-VALUE
	     (VLAX-INVOKE-METHOD ENT_OBJECT "GETATTRIBUTES")
	   )
	 )
  )

  (SETQ I 0)
  (SETQ LIST1 NIL)
  (WHILE (< I (LENGTH SAFEARRAY_SET))

    (IF (= (vlax-get-property (NTH I SAFEARRAY_SET) 'TAGSTRING) ATTRIBUTE_NAME)
      
    (vlax-put-property (NTH I SAFEARRAY_SET) 'ROTATION TEMP_ROTATION)
      
    )
    (IF (= (vlax-get-property (NTH I SAFEARRAY_SET) 'TAGSTRING) ATTRIBUTE_NAME)
      
    (vlax-put-property (NTH I SAFEARRAY_SET) 'ROTATION TEMP_ROTATION)
      
    )

    (SETQ I (+ I 1))
  )

  
)

 ))



(DEFUN INSERT_OBSTRUCTIONS_GPS ( OBSTRUCTION_LIST KM_STONE_COORDINATES TRACK_ENTITY_UPTRACK TRACK_ENTITY_DNTRACK TRACK_ENTITY_CENTERLINE DIRECTION / I X-COORDINATE Y-COORDINATE BRNO )
  (SETQ I 0)
  (WHILE (< I (LENGTH OBSTRUCTION_LIST))
    (IF (/= (ASSOC (ITOA (FIX (NTH 0 (NTH I OBSTRUCTION_LIST)))) KM_STONE_COORDINATES) NIL)
    (PROGN
    (SETQ CONT_KM (FIX (/ (NTH 6 (NTH I OBSTRUCTION_LIST)) 1000)))
    (SETQ CONT_CH (- (NTH 6 (NTH I OBSTRUCTION_LIST)) (* CONT_KM 1000)))
    (IF (/= (VL-POSITION (NTH 2 (NTH I OBSTRUCTION_LIST)) (LIST "ROB" "RUB" "RFO" "BRIDGE" "MINOR BRIDGE" "MAJOR BRIDGE" "CULVERT")) NIL)
    (PROGN
    (SETQ INSERTION_INFO (GET_OBSTRUCTION_CO-ORDINATES (ASSOC (ITOA (FIX (NTH 0 (NTH I OBSTRUCTION_LIST)))) KM_STONE_COORDINATES) (NTH 1 (NTH I OBSTRUCTION_LIST)) TRACK_ENTITY_UPTRACK TRACK_ENTITY_CENTERLINE DIRECTION))
    (COMMAND "INSERT" "BRIDGE_2" (NTH 0 INSERTION_INFO)  "1" (* (/ 180 PI) (NTH 1 INSERTION_INFO)))
    (INSERT_DYNAMIC_PROPERTIES (ENTLAST) (LIST "WIDTH" "ADJ" "KM" "CHAINAGE" "TYPE" "CONTINUOUS_KM" "CONTINUOUS_CHAINAGE" "REPRESENTATION_LENGTH") (LIST (NTH 4 (NTH I OBSTRUCTION_LIST)) 50 (NTH 0 (NTH I OBSTRUCTION_LIST)) (NTH 1 (NTH I OBSTRUCTION_LIST)) (NTH 2 (NTH I OBSTRUCTION_LIST)) CONT_KM CONT_CH 25))
    (IF (/= (NTH 5 (NTH I OBSTRUCTION_LIST)) NIL)
    (PROGN
    (IF (/= (TYPE (NTH 5 (NTH I OBSTRUCTION_LIST))) 'STR) (SETQ BRNO (RTOS (NTH 5 (NTH I OBSTRUCTION_LIST)) 2 0)) (SETQ BRNO (NTH 5 (NTH I OBSTRUCTION_LIST))))
    (MODIFY_ATTRIBUTES (ENTLAST) (LIST "BRIDGE_NO.") (LIST (STRCAT (NTH 2 (NTH I OBSTRUCTION_LIST)) " NO.:" BRNO)))
    )
    (PROGN
    (INSERT_DYNAMIC_PROPERTIES (ENTLAST) (LIST "BRV1") (LIST "WITHOUT BRIDGE NUMBER"))
    )
    )
    )
    )

    (IF (/= (VL-POSITION (NTH 2 (NTH I OBSTRUCTION_LIST)) (LIST "FOB" "SUB WAY")) NIL)
    (PROGN
    (SETQ INSERTION_INFO (GET_OBSTRUCTION_CO-ORDINATES (ASSOC (ITOA (FIX (NTH 0 (NTH I OBSTRUCTION_LIST)))) KM_STONE_COORDINATES) (NTH 1 (NTH I OBSTRUCTION_LIST)) TRACK_ENTITY_UPTRACK TRACK_ENTITY_CENTERLINE DIRECTION))
    (COMMAND "INSERT" "FOB_SUBWAY" (NTH 0 INSERTION_INFO)  "1" (* (/ 180 PI) (NTH 1 INSERTION_INFO)))
    
    (INSERT_DYNAMIC_PROPERTIES (ENTLAST) (LIST "WIDTH" "ADJ" "KM" "CHAINAGE" "TYPE" "REPRESENTATION_LENGTH") (LIST (NTH 4 (NTH I OBSTRUCTION_LIST)) 50 (NTH 0 (NTH I OBSTRUCTION_LIST)) (NTH 1 (NTH I OBSTRUCTION_LIST)) (NTH 2 (NTH I OBSTRUCTION_LIST)) 25))
    (IF (/= (NTH 5 (NTH I OBSTRUCTION_LIST)) NIL)
    (PROGN
    (IF (/= (TYPE (NTH 5 (NTH I OBSTRUCTION_LIST))) 'STR) (SETQ BRNO (RTOS (NTH 5 (NTH I OBSTRUCTION_LIST)) 2 0)) (SETQ BRNO (NTH 5 (NTH I OBSTRUCTION_LIST))))
    (MODIFY_ATTRIBUTES (ENTLAST) (LIST "BRIDGE_NO.") (LIST (STRCAT (NTH 2 (NTH I OBSTRUCTION_LIST)) " NO.:" BRNO)))
    )
    (PROGN
    (INSERT_DYNAMIC_PROPERTIES (ENTLAST) (LIST "BRV1") (LIST "WITHOUT BRIDGE NUMBER"))
    )
    )
    ))

    (IF (/= (VL-POSITION (NTH 2 (NTH I OBSTRUCTION_LIST)) (LIST "POWER LINE CROSSING")) NIL)
    (PROGN
    (SETQ INSERTION_INFO (GET_OBSTRUCTION_CO-ORDINATES (ASSOC (ITOA (FIX (NTH 0 (NTH I OBSTRUCTION_LIST)))) KM_STONE_COORDINATES) (NTH 1 (NTH I OBSTRUCTION_LIST)) TRACK_ENTITY_UPTRACK TRACK_ENTITY_CENTERLINE DIRECTION))
    (COMMAND "INSERT" "POWER LINE CROSSING" (NTH 0 INSERTION_INFO)  "1" (* (/ 180 PI) (NTH 1 INSERTION_INFO)))
    )
    )

    (IF (/= (VL-POSITION (NTH 2 (NTH I OBSTRUCTION_LIST)) (LIST "SIGNAL DN")) NIL)
    (PROGN
    (SETQ INSERTION_INFO (GET_OBSTRUCTION_CO-ORDINATES (ASSOC (ITOA (FIX (NTH 0 (NTH I OBSTRUCTION_LIST)))) KM_STONE_COORDINATES) (NTH 1 (NTH I OBSTRUCTION_LIST)) TRACK_ENTITY_UPTRACK TRACK_ENTITY_UPTRACK DIRECTION))
    (COMMAND "INSERT" "SIGNAL_NEW" (NTH 0 INSERTION_INFO)  "1" "0")
    (INSERT_DYNAMIC_PROPERTIES (ENTLAST) (LIST "A1" "D2" "ADJ" "REPRESENTATION_LENGTH") (LIST (NTH 1 INSERTION_INFO) 5.75 47 25))
    (CHANGE_ATTRIBUTE_ROTATION1 (ENTLAST) "IMPLANTATION1" (NTH 1 INSERTION_INFO))
    (MODIFY_ATTRIBUTES (ENTLAST) (LIST "TEXT1" "TEXT2" "TEXT3") (LIST (STRCAT "DFCC CH:" (ITOA (FIX (NTH 0 (NTH I OBSTRUCTION_LIST)))) "/" (RTOS (NTH 1 (NTH I OBSTRUCTION_LIST)) 2 2)) (STRCAT "SIGNAL " (RTOS (NTH 4 (NTH I OBSTRUCTION_LIST)) 2 0)) (STRCAT "CONT. CH:" (ITOA CONT_KM) "/" (RTOS CONT_CH 2 2))))
    ))

    (IF (/= (VL-POSITION (NTH 2 (NTH I OBSTRUCTION_LIST)) (LIST "SIGNAL UP")) NIL)
    (PROGN
    (SETQ INSERTION_INFO (GET_OBSTRUCTION_CO-ORDINATES (ASSOC (ITOA (FIX (NTH 0 (NTH I OBSTRUCTION_LIST)))) KM_STONE_COORDINATES) (NTH 1 (NTH I OBSTRUCTION_LIST)) TRACK_ENTITY_UPTRACK TRACK_ENTITY_DNTRACK DIRECTION))
    (COMMAND "INSERT" "SIGNAL_NEW" (NTH 0 INSERTION_INFO)  "1" "0")
    (INSERT_DYNAMIC_PROPERTIES (ENTLAST) (LIST "A1" "D2" "ADJ" "REPRESENTATION_LENGTH") (LIST (+ PI (NTH 1 INSERTION_INFO)) 5.75 47 25))
    (MODIFY_ATTRIBUTES (ENTLAST) (LIST "TEXT1" "TEXT2" "TEXT3") (LIST (STRCAT "DFCC CH:" (ITOA (FIX (NTH 0 (NTH I OBSTRUCTION_LIST)))) "/" (RTOS (NTH 1 (NTH I OBSTRUCTION_LIST)) 2 2)) (STRCAT "SIGNAL " (RTOS (NTH 4 (NTH I OBSTRUCTION_LIST)) 2 0)) (STRCAT "CONT. CH:" (ITOA CONT_KM) "/" (RTOS CONT_CH 2 2))))
    ))
    
    (IF (/= (VL-POSITION (NTH 2 (NTH I OBSTRUCTION_LIST)) (LIST "CURVE START" "CURVE END" "TS" "SC" "CS" "ST")) NIL)
    (PROGN
    (SETQ INSERTION_INFO1 (GET_OBSTRUCTION_CO-ORDINATES (ASSOC (ITOA (FIX (NTH 0 (NTH I OBSTRUCTION_LIST)))) KM_STONE_COORDINATES) (NTH 1 (NTH I OBSTRUCTION_LIST)) TRACK_ENTITY_UPTRACK TRACK_ENTITY_UPTRACK DIRECTION))
    (COMMAND "INSERT" "CURVE_SYMBOL1" (NTH 0 INSERTION_INFO1)  "1" "0")
    (MODIFY_ATTRIBUTES (ENTLAST) (LIST "TEXT1" "TEXT2" "TEXT3") (LIST (STRCAT "DFCC CH:" (ITOA (FIX (NTH 0 (NTH I OBSTRUCTION_LIST)))) "/" (RTOS (NTH 1 (NTH I OBSTRUCTION_LIST)) 2 2)) (NTH 2 (NTH I OBSTRUCTION_LIST)) (STRCAT "CONT. CH:" (ITOA CONT_KM) "/" (RTOS CONT_CH 2 2))))
    (INSERT_DYNAMIC_PROPERTIES (ENTLAST) (LIST "CR1" "ADJ" "REPRESENTATION_LENGTH") (LIST (NTH 1 INSERTION_INFO1) 47 25))
    (SETQ INSERTION_INFO2 (GET_OBSTRUCTION_CO-ORDINATES (ASSOC (ITOA (FIX (NTH 0 (NTH I OBSTRUCTION_LIST)))) KM_STONE_COORDINATES) (NTH 1 (NTH I OBSTRUCTION_LIST)) TRACK_ENTITY_UPTRACK TRACK_ENTITY_DNTRACK DIRECTION))
    (COMMAND "INSERT" "CURVE_SYMBOL" (NTH 0 INSERTION_INFO2)  "1" "0")
    (INSERT_DYNAMIC_PROPERTIES (ENTLAST) (LIST "CR1") (LIST (+ PI (NTH 1 INSERTION_INFO2))))
    (IF (/= (VL-POSITION (NTH 2 (NTH I OBSTRUCTION_LIST)) (LIST "CURVE START" "TS")) NIL)
      (COMMAND "INSERT" "CURVE_DETAILS" (POLAR (NTH 0 INSERTION_INFO1) (+ 1.23 (NTH 1 INSERTION_INFO1)) 40)   "1" (* (/ 180 PI) (NTH 1 INSERTION_INFO1)) )
    )
    (IF (/= (NTH 4 (NTH I OBSTRUCTION_LIST)) NIL) (MODIFY_ATTRIBUTES (ENTLAST) (LIST "CURVE_RADIUS") (LIST (NTH 4 (NTH I OBSTRUCTION_LIST)))))
    (IF (/= (NTH 5 (NTH I OBSTRUCTION_LIST)) NIL) (MODIFY_ATTRIBUTES (ENTLAST) (LIST "CURVE_NO") (LIST (NTH 5 (NTH I OBSTRUCTION_LIST)))))
    )
    )


    (IF (/= (VL-POSITION (NTH 2 (NTH I OBSTRUCTION_LIST)) (LIST "G.POST")) NIL)
    (PROGN
    (SETQ INSERTION_INFO1 (GET_OBSTRUCTION_CO-ORDINATES (ASSOC (ITOA (FIX (NTH 0 (NTH I OBSTRUCTION_LIST)))) KM_STONE_COORDINATES) (NTH 1 (NTH I OBSTRUCTION_LIST)) TRACK_ENTITY_UPTRACK TRACK_ENTITY_UPTRACK DIRECTION))
    (COMMAND "INSERT" "GRADIENT_POST" (POLAR (NTH 0 INSERTION_INFO1) (+ (/ PI 2) (NTH 1 INSERTION_INFO1)) 15)   "1" (* (/ 180 PI) (NTH 1 INSERTION_INFO1)) )
    (MODIFY_ATTRIBUTES (ENTLAST) (LIST "TEXT1" "TEXT2" "TEXT3") (LIST (STRCAT "DFCC CH:" (ITOA (FIX (NTH 0 (NTH I OBSTRUCTION_LIST)))) "/" (RTOS (NTH 1 (NTH I OBSTRUCTION_LIST)) 2 2)) (NTH 2 (NTH I OBSTRUCTION_LIST)) (STRCAT "CONT. CH:" (ITOA CONT_KM) "/" (RTOS CONT_CH 2 2))))
    (MODIFY_ATTRIBUTES (ENTLAST) (LIST "LEFT_GRADIENT" "RIGHT_GRADIENT" ) (LIST (STRCAT (RTOS (ABS (NTH 4 (NTH I OBSTRUCTION_LIST))) 2 3) "%") (STRCAT (RTOS (ABS (NTH 5 (NTH I OBSTRUCTION_LIST))) 2 3) "%")))
    (INSERT_DYNAMIC_PROPERTIES (ENTLAST) (LIST "ADJ" "REPRESENTATION_LENGTH") (LIST  32 25))
    (IF (> (NTH 4 (NTH I OBSTRUCTION_LIST)) 0)
      (PROGN
      (INSERT_DYNAMIC_PROPERTIES (ENTLAST) (LIST "STR2") (LIST  (* (/ PI 180) 164.09)))
      (MODIFY_ATTRIBUTES (ENTLAST) (LIST "LEFT_DIRECTION" ) (LIST "FALL"))
      )
      (PROGN
      (INSERT_DYNAMIC_PROPERTIES (ENTLAST) (LIST "STR2") (LIST (* (/ PI 180) 194.09) ))
      (MODIFY_ATTRIBUTES (ENTLAST) (LIST "LEFT_DIRECTION" ) (LIST "RISE"))
      )
    )

    (IF (> (NTH 5 (NTH I OBSTRUCTION_LIST)) 0)
      (PROGN
      (INSERT_DYNAMIC_PROPERTIES (ENTLAST) (LIST "STR1") (LIST (* (/ PI 180) 15.91) ) )
      (MODIFY_ATTRIBUTES (ENTLAST) (LIST "RIGHT_DIRECTION" ) (LIST "RISE"))
      )
      (PROGN
      (INSERT_DYNAMIC_PROPERTIES (ENTLAST) (LIST "STR1") (LIST (* (/ PI 180) 345.91)))
      (MODIFY_ATTRIBUTES (ENTLAST) (LIST "RIGHT_DIRECTION" ) (LIST "FALL"))
      )
    )
    
    )
    )


    (IF (/= (VL-POSITION (NTH 2 (NTH I OBSTRUCTION_LIST)) (LIST "PIPELINE CROSSING")) NIL)
    (PROGN
    (SETQ INSERTION_INFO1 (GET_OBSTRUCTION_CO-ORDINATES (ASSOC (ITOA (FIX (NTH 0 (NTH I OBSTRUCTION_LIST)))) KM_STONE_COORDINATES) (NTH 1 (NTH I OBSTRUCTION_LIST)) TRACK_ENTITY_UPTRACK TRACK_ENTITY_UPTRACK DIRECTION))
    (COMMAND "INSERT" "UG_PIPELINE_CROSSING" (NTH 0 INSERTION_INFO1)   "1" (* (/ 180 PI) (NTH 1 INSERTION_INFO1)) )
    (MODIFY_ATTRIBUTES (ENTLAST) (LIST "TEXT1" "TEXT2" "TEXT3") (LIST (STRCAT "DFCC CH:" (ITOA (FIX (NTH 0 (NTH I OBSTRUCTION_LIST)))) "/" (RTOS (NTH 1 (NTH I OBSTRUCTION_LIST)) 2 2)) (NTH 2 (NTH I OBSTRUCTION_LIST)) (STRCAT "CONT. CH:" (ITOA CONT_KM) "/" (RTOS CONT_CH 2 2))))
    (INSERT_DYNAMIC_PROPERTIES (ENTLAST) (LIST "ADJ" "REPRESENTATION_LENGTH") (LIST 47 25))

    (IF (/= (NTH 5 (NTH I OBSTRUCTION_LIST)) NIL)
    (PROGN
    (IF (/= (TYPE (NTH 5 (NTH I OBSTRUCTION_LIST))) 'STR) (SETQ BRNO (RTOS (NTH 5 (NTH I OBSTRUCTION_LIST)) 2 0)) (SETQ BRNO (NTH 5 (NTH I OBSTRUCTION_LIST))))
     (INSERT_DYNAMIC_PROPERTIES (ENTLAST) (LIST "WIDTH" "BRV1") (LIST (NTH 5 (NTH I OBSTRUCTION_LIST)) "WITH DIAMETER"))
    (MODIFY_ATTRIBUTES (ENTLAST) (LIST "DIAMETER") (LIST (STRCAT "DIAMETER = " (RTOS (NTH 5 (NTH I OBSTRUCTION_LIST)) 2 2) " M")))
    )
    (PROGN
    (INSERT_DYNAMIC_PROPERTIES (ENTLAST) (LIST "BRV1") (LIST "WITHOUT DIAMETER"))
    )
    )

    
    )
    )

    (IF (/= (VL-POSITION (NTH 2 (NTH I OBSTRUCTION_LIST)) (LIST "UG CABLE")) NIL)
    (PROGN
    (SETQ INSERTION_INFO1 (GET_OBSTRUCTION_CO-ORDINATES (ASSOC (ITOA (FIX (NTH 0 (NTH I OBSTRUCTION_LIST)))) KM_STONE_COORDINATES) (NTH 1 (NTH I OBSTRUCTION_LIST)) TRACK_ENTITY_UPTRACK TRACK_ENTITY_UPTRACK DIRECTION))
    (COMMAND "INSERT" "UG_CABLE" (NTH 0 INSERTION_INFO1)   "1" (* (/ 180 PI) (NTH 1 INSERTION_INFO1)) )
    (MODIFY_ATTRIBUTES (ENTLAST) (LIST "TEXT1" "TEXT2" "TEXT3") (LIST (STRCAT "DFCC CH:" (ITOA (FIX (NTH 0 (NTH I OBSTRUCTION_LIST)))) "/" (RTOS (NTH 1 (NTH I OBSTRUCTION_LIST)) 2 2)) (NTH 2 (NTH I OBSTRUCTION_LIST)) (STRCAT "CONT. CH:" (ITOA CONT_KM) "/" (RTOS CONT_CH 2 2))))
    (INSERT_DYNAMIC_PROPERTIES (ENTLAST) (LIST "ADJ" "REPRESENTATION_LENGTH") (LIST 47 25))

    (IF (/= (NTH 5 (NTH I OBSTRUCTION_LIST)) NIL)
    (PROGN
    (IF (/= (TYPE (NTH 5 (NTH I OBSTRUCTION_LIST))) 'STR) (SETQ BRNO (RTOS (NTH 5 (NTH I OBSTRUCTION_LIST)) 2 0)) (SETQ BRNO (NTH 5 (NTH I OBSTRUCTION_LIST))))
    (INSERT_DYNAMIC_PROPERTIES (ENTLAST) (LIST "BRV1") (LIST "WITH VOLTAGE"))
    (MODIFY_ATTRIBUTES (ENTLAST) (LIST "VOLTAGE") (LIST (STRCAT "VOLTAGE = " (RTOS (NTH 5 (NTH I OBSTRUCTION_LIST)) 2 2) " kV")))
    )
    (PROGN
    (INSERT_DYNAMIC_PROPERTIES (ENTLAST) (LIST "BRV1") (LIST "WITHOUT VOLTAGE"))
    )
    )
    
    )
    )


    (IF (= (VL-POSITION (NTH 2 (NTH I OBSTRUCTION_LIST)) (LIST "ROB" "RUB" "RFO" "BRIDGE" "MINOR BRIDGE" "MAJOR BRIDGE" "CULVERT" "FOB" "SUB WAY" "POWER LINE CROSSING" "SIGNAL DN" "SIGNAL UP" "CURVE START" "CURVE END" "TS" "SC" "CS" "ST" "G.POST" "PIPELINE CROSSING" "UG CABLE")) NIL)
    (PROGN
    (IF (= (NTH 3 (NTH I OBSTRUCTION_LIST)) "DN")
    (PROGN 
    (SETQ INSERTION_INFO (GET_OBSTRUCTION_CO-ORDINATES (ASSOC (ITOA (FIX (NTH 0 (NTH I OBSTRUCTION_LIST)))) KM_STONE_COORDINATES) (NTH 1 (NTH I OBSTRUCTION_LIST)) TRACK_ENTITY_UPTRACK TRACK_ENTITY_UPTRACK DIRECTION))
    (COMMAND "INSERT" "REPRESENTATION1" (NTH 0 INSERTION_INFO)  "1" (* (/ 180 PI) (NTH 1 INSERTION_INFO)))
    (INSERT_DYNAMIC_PROPERTIES (ENTLAST) (LIST "ADJ" "REPRESENTATION_LENGTH") (LIST 47 25))
    )
    
    (PROGN
    (SETQ INSERTION_INFO (GET_OBSTRUCTION_CO-ORDINATES (ASSOC (ITOA (FIX (NTH 0 (NTH I OBSTRUCTION_LIST)))) KM_STONE_COORDINATES) (NTH 1 (NTH I OBSTRUCTION_LIST)) TRACK_ENTITY_UPTRACK TRACK_ENTITY_DNTRACK DIRECTION))
    (COMMAND "INSERT" "REPRESENTATION1" (NTH 0 INSERTION_INFO)  "1" (+ 180 (* (/ 180 PI) (NTH 1 INSERTION_INFO))))
    (INSERT_DYNAMIC_PROPERTIES (ENTLAST) (LIST "STF1" "ADJ" "REPRESENTATION_LENGTH") (LIST "1" 47 25))
    )
    )
    
    (MODIFY_ATTRIBUTES (ENTLAST) (LIST "TEXT1" "TEXT2" "TEXT3") (LIST (STRCAT "DFCC CH:" (ITOA (FIX (NTH 0 (NTH I OBSTRUCTION_LIST)))) "/" (RTOS (NTH 1 (NTH I OBSTRUCTION_LIST)) 2 2)) (NTH 2 (NTH I OBSTRUCTION_LIST)) (STRCAT "CONT. CH:" (ITOA CONT_KM) "/" (RTOS CONT_CH 2 2))))
    
    )
    )

    
    
    )
    )
    
    (SETQ I (+ I 1))
  )
)





(DEFUN GET_OBSTRUCTION_CO-ORDINATES ( KM_DATA CHAINAGE REFERENCE_POLYLINE MAIN_POLYLINE DIRECTION / MAIN_POINT ANGLE1 DERIVATIVE SLOPE)
  (SETQ START_POINT (NTH 1 KM_DATA) TEMP_DISTANCE NIL MAIN_POINT NIL ANGLE1 NIL DERIVATIVE NIL SLOPE NIL)
  (SETQ TEMP_DISTANCE (VLAX-CURVE-GETDISTATPOINT REFERENCE_POLYLINE (NTH 1 KM_DATA)))
    (IF (= DIRECTION "POSITIVE")
      (SETQ TEMP_DISTANCE (- TEMP_DISTANCE CHAINAGE))
      (SETQ TEMP_DISTANCE (+ TEMP_DISTANCE CHAINAGE))
    )
  (SETQ POINT_ON_REFERENCE_TRACK (VLAX-CURVE-GETPOINTATDIST REFERENCE_POLYLINE TEMP_DISTANCE))
  (IF (/= REFERENCE_POLYLINE MAIN_POLYLINE)
  (SETQ MAIN_POINT (VLAX-CURVE-GETCLOSESTPOINTTO MAIN_POLYLINE POINT_ON_REFERENCE_TRACK T))
  (SETQ MAIN_POINT POINT_ON_REFERENCE_TRACK)
  )
  
  (SETQ ANGLE1 (VLAX-CURVE-GETPARAMATPOINT MAIN_POLYLINE MAIN_POINT))
  
  (SETQ DERIVATIVE (VLAX-CURVE-GETFIRSTDERIV MAIN_POLYLINE ANGLE1))
  
  (SETQ SLOPE (ANGLE '(0 0 0) DERIVATIVE))

  (LIST MAIN_POINT SLOPE)

)







(DEFUN C:KM_STONE_GPS ( / TRACK_ENTITY_UPTRACK WPT1 WPT2 DIRECTION NUMBER KM KM_STONE_LIST BLOCKS_LIST BLOCK_NAME_LIST KM_STONE_LIST I)
 (SETQ TRACK_ENTITY_UPTRACK (CAR(ENTSEL "\nSELECT REFERENCE TRACK ALIGNMENT:")))
 (SETQ WPT1 (GETPOINT "SELECT STARTING POINT ON REFERENCE TRACK ALIGNMENT"))
 (SETQ WPT2 (GETPOINT "\n PICK ANY POINT ON CURVE IN REQUIRED DIRECTION "))
 (SETQ DIRECTION (FIND_DIRECTION TRACK_ENTITY_UPTRACK WPT1 WPT2))
 (SETQ NUMBER (GETINT "\n ENTER KM COUNT"))
 (SETQ KM (GETSTRING "\n ENTER STARTING KM IN LOP"))
 (SETQ KM_STONE_LIST (INSERT_KM_STONE_GPS TRACK_ENTITY_UPTRACK WPT1 NUMBER DIRECTION))
 (SETQ I 0)
 (WHILE (< I (LENGTH KM_STONE_LIST))
  (MODIFY_ATTRIBUTES (NTH 0 (NTH I KM_STONE_LIST)) (LIST "KM" "LEFT_KM" "RIGHT_KM") (LIST (STRCAT "%%UCONT KM:" KM) (STRCAT (ITOA (- (ATOI KM) 1)) "/1000.00" ) (STRCAT (ITOA (ATOI KM)) "/0000.00" )))
  (SETQ KM (ITOA (+ (ATOI KM) 1)))
  (SETQ I (+ I 1))
 )
)


(DEFUN C:DFCC_KM_STONE_GPS ( / TRACK_ENTITY_UPTRACK WPT1 WPT2 DIRECTION NUMBER KM KM_STONE_LIST BLOCKS_LIST BLOCK_NAME_LIST KM_STONE_LIST I)
 (SETQ TRACK_ENTITY_UPTRACK (CAR(ENTSEL "\nSELECT REFERENCE TRACK ALIGNMENT:")))
 (SETQ WPT1 (GETPOINT "SELECT STARTING POINT ON REFERENCE TRACK ALIGNMENT"))
 (SETQ WPT2 (GETPOINT "\n PICK ANY POINT ON CURVE IN REQUIRED DIRECTION "))
 (SETQ DIRECTION (FIND_DIRECTION TRACK_ENTITY_UPTRACK WPT1 WPT2))
 (SETQ NUMBER (GETINT "\n ENTER KM COUNT"))
 (SETQ KM (GETSTRING "\n ENTER STARTING KM IN LOP"))
 (SETQ KM_STONE_LIST (INSERT_KM_STONE_GPS1 TRACK_ENTITY_UPTRACK WPT1 NUMBER DIRECTION))
 (SETQ I 0)
 (WHILE (< I (LENGTH KM_STONE_LIST))
  (MODIFY_ATTRIBUTES (NTH 0 (NTH I KM_STONE_LIST)) (LIST "KM" "LEFT_KM" "RIGHT_KM") (LIST (STRCAT "%%UKM:" KM) (STRCAT (ITOA (- (ATOI KM) 1)) "/1000.00" ) (STRCAT (ITOA (ATOI KM)) "/0000.00" )))
  (SETQ KM (ITOA (+ (ATOI KM) 1)))
  (SETQ I (+ I 1))
 )
)


(DEFUN INSERT_KM_STONE_GPS ( TRACK_ENTITY_UPTRACK STARTING_POINT NUMBER DIRECTION  / I FINAL_LIST ROTATION TEMP_DISTANCE ) 
(SETQ I 0 FINAL_LIST NIL ROTATION NIL TEMP_DISTANCE NIL)
  (WHILE (< I NUMBER)
    (SETQ ROTATION (GET_KM_ROTATION TRACK_ENTITY_UPTRACK STARTING_POINT))
    (COMMAND "INSERT" "KM_NEW" (POLAR STARTING_POINT (+ (/ PI 2) ROTATION) 52) "1" (* (/ 180 PI) ROTATION))
    (SETQ FINAL_LIST (CONS (LIST (ENTLAST) STARTING_POINT) FINAL_LIST))
      (SETQ TEMP_DISTANCE (VLAX-CURVE-GETDISTATPOINT TRACK_ENTITY_UPTRACK STARTING_POINT))
    (IF (= DIRECTION "POSITIVE")
      (SETQ TEMP_DISTANCE (- TEMP_DISTANCE 1000))
      (SETQ TEMP_DISTANCE (+ TEMP_DISTANCE 1000))
    )
   (SETQ STARTING_POINT (VLAX-CURVE-GETPOINTATDIST TRACK_ENTITY_UPTRACK TEMP_DISTANCE))

    (SETQ I (+ I 1))
  )
(REVERSE FINAL_LIST)
)

(DEFUN INSERT_KM_STONE_GPS1 ( TRACK_ENTITY_UPTRACK STARTING_POINT NUMBER DIRECTION  / I FINAL_LIST ROTATION TEMP_DISTANCE ) 
(SETQ I 0 FINAL_LIST NIL ROTATION NIL TEMP_DISTANCE NIL)
  (WHILE (< I NUMBER)
    (SETQ ROTATION (GET_KM_ROTATION TRACK_ENTITY_UPTRACK STARTING_POINT))
    (COMMAND "INSERT" "DFCC_KM_NEW" (POLAR STARTING_POINT (+ (/ PI 2) ROTATION) 52) "1" (* (/ 180 PI) ROTATION))
    (SETQ FINAL_LIST (CONS (LIST (ENTLAST) STARTING_POINT) FINAL_LIST))
      (SETQ TEMP_DISTANCE (VLAX-CURVE-GETDISTATPOINT TRACK_ENTITY_UPTRACK STARTING_POINT))
    (IF (= DIRECTION "POSITIVE")
      (SETQ TEMP_DISTANCE (- TEMP_DISTANCE 1000))
      (SETQ TEMP_DISTANCE (+ TEMP_DISTANCE 1000))
    )
   (SETQ STARTING_POINT (VLAX-CURVE-GETPOINTATDIST TRACK_ENTITY_UPTRACK TEMP_DISTANCE))

    (SETQ I (+ I 1))
  )
(REVERSE FINAL_LIST)
)


(DEFUN GET_KM_ROTATION (REFERENCE_POLYLINE POINT1 / MAIN_POINT ANGLE1 DERIVATIVE SLOPE)
  
  (SETQ TEMP_DISTANCE NIL MAIN_POINT NIL ANGLE1 NIL DERIVATIVE NIL SLOPE NIL)
  
  (SETQ ANGLE1 (VLAX-CURVE-GETPARAMATPOINT REFERENCE_POLYLINE POINT1))
  
  (SETQ DERIVATIVE (VLAX-CURVE-GETFIRSTDERIV REFERENCE_POLYLINE ANGLE1))
  
  (SETQ SLOPE (ANGLE '(0 0 0) DERIVATIVE))

  SLOPE

)




(DEFUN GET_SPAN_DETAILS ( ENT_LIST  / ENT_LIST I TEMP_CHAINAGE TEMP_EFFNAME TEMP_SPAN FINAL_LIST)
  (SETQ ENT_LIST (EXTRACT_ENTITY_INFO ENT_LIST 1 3))
  (SETQ ENT_LIST (SORT_FUN ENT_LIST 1 0))
  (SETQ ENT_LIST (SINGLE_ELE_LIST ENT_LIST 0))
  (SETQ I 0 TEMP_CHAINAGE NIL TEMP_EFFNAME NIL TEMP_SPAN NIL FINAL_LIST NIL)
  (WHILE (< I (LENGTH ENT_LIST))
    (SETQ TEMP_CHAINAGE (NTH 0 (SINGLE_ELE_LIST (EXTRACT_ATTRIBUTES (NTH I ENT_LIST) (LIST "CHAINAGE1" ) 1) 1)))
    (SETQ TEMP_EFFNAME (VLAX-GET-PROPERTY (VLAX-ENAME->VLA-OBJECT (NTH I ENT_LIST)) 'EFFECTIVENAME))
    (SETQ TEMP_SPAN (NTH 0 (SINGLE_ELE_LIST (EXTRACT_ATTRIBUTES (NTH I ENT_LIST) (LIST "SPAN1" ) 1) 1)))
    (SETQ FINAL_LIST (CONS (LIST TEMP_CHAINAGE TEMP_EFFNAME TEMP_SPAN) FINAL_LIST))
    (SETQ I (+ I 1))
  )
  (REVERSE FINAL_LIST)
 )



(DEFUN GET_CO-ORDINATES ( ENT_LIST  / ENT_LIST I TEMP_CHAINAGE TEMP_EFFNAME TEMP_SPAN FINAL_LIST)
  (SETQ ENT_LIST (EXTRACT_ENTITY_INFO ENT_LIST 1 3))
  (SETQ ENT_LIST (SORT_FUN ENT_LIST 1 0))
  (SETQ ENT_LIST (SINGLE_ELE_LIST ENT_LIST 0))
  (SETQ I 0 TEMP_CHAINAGE NIL TEMP_EFFNAME NIL TEMP_SPAN NIL FINAL_LIST NIL)
  (WHILE (< I (LENGTH ENT_LIST))
    (SETQ TEMP_NUMBER (NTH 0 (SINGLE_ELE_LIST (EXTRACT_ATTRIBUTES (NTH I ENT_LIST) (LIST "MAST_NUMBER1" ) 1) 1)))
    (SETQ TEMP_CHAINAGE (NTH 0 (SINGLE_ELE_LIST (EXTRACT_ATTRIBUTES (NTH I ENT_LIST) (LIST "CHAINAGE1" ) 1) 1)))
    (SETQ TEMP_EFFNAME (VLAX-GET-PROPERTY (VLAX-ENAME->VLA-OBJECT (NTH I ENT_LIST)) 'EFFECTIVENAME))
    (SETQ TEMP_SPAN (NTH 0 (SINGLE_ELE_LIST (EXTRACT_ATTRIBUTES (NTH I ENT_LIST) (LIST "SPAN1" ) 1) 1)))
    (SETQ TEMP_CO-ORDINATES (CDR (ASSOC 10 (ENTGET (NTH I ENT_LIST)))))
    (SETQ FINAL_LIST (CONS (APPEND (LIST TEMP_NUMBER TEMP_CHAINAGE TEMP_EFFNAME TEMP_SPAN) TEMP_CO-ORDINATES) FINAL_LIST))
    (SETQ I (+ I 1))
  )
  (REVERSE FINAL_LIST)
)

(DEFUN C:LOAD_EXCEL_GPS ( / )
  (OPENEXCEL (FINDFILE "SPANEXTRACT.XLSX") "Sheet1" T)
)

(DEFUN C:LOAD_SPAN_EXTRACTION_FILE ( / )
  (OPENEXCEL (FINDFILE (GETFILED "SELECT OBSTRUCTION FILE" "" "" 8)) "Sheet1" T)
)

(DEFUN SORT_MASTS (ENT_LIST STARTING_MAST / I TEMP_DIST FINAL_LIST )
  (SETQ TEMP_MAST (ASSOC STARTING_MAST ENT_LIST))
  (SETQ I 0 TEMP_DIST NIL FINAL_LIST NIL)
  (WHILE (< I (LENGTH ENT_LIST))
    (SETQ TEMP_DIST (DISTANCE (NTH 1 TEMP_MAST) (NTH 1 (NTH I ENT_LIST))))
    (SETQ FINAL_LIST (CONS (APPEND (NTH I ENT_LIST) (LIST TEMP_DIST)) FINAL_LIST))
    (SETQ I (+ I 1))
  )
  (SORT_FUN (REVERSE FINAL_LIST) 0 2)
)





(DEFUN IMPORT_SPAN_LENGTHS_FROM_MASTS ( / )
   (SETQ SSSET (SSGET))
   (SETQ STARTING_MAST (CAR(ENTSEL "N/ SELECT STARTING MAST")))
   (SETQ TRACK_CENTER (CAR(ENTSEL "N/ SELECT TRACK CENTER")))
   (SETQ STARTING_CELL (GETSTRING "N/ ENTER STARTING CELL"))
   (SETQ ENT_LIST (FORM_SSSET SSSET))
   (SETQ ENT_LIST (EXTRACT_ENTITY_INFO ENT_LIST 1 3))
   (SETQ ENT_LIST (SORT_MASTS ENT_LIST STARTING_MAST))
    (SETQ DETAILS_TO_PRINT (GET_CO-ORDINATES (SINGLE_ELE_LIST ENT_LIST 0)))
    (PUTCELLSHEET "Sheet1" (COLUMN+N STARTING_CELL 0) (SINGLE_ELE_LIST DETAILS_TO_PRINT 0))
    (PUTCELLSHEET "Sheet1" (COLUMN+N STARTING_CELL 1) (SINGLE_ELE_LIST DETAILS_TO_PRINT 1))
    (PUTCELLSHEET "Sheet1" (COLUMN+N STARTING_CELL 2) (SINGLE_ELE_LIST DETAILS_TO_PRINT 2))
    (PUTCELLSHEET "Sheet1" (COLUMN+N STARTING_CELL 3) (SINGLE_ELE_LIST DETAILS_TO_PRINT 3))
    (PUTCELLSHEET "Sheet1" (COLUMN+N STARTING_CELL 4) (SINGLE_ELE_LIST DETAILS_TO_PRINT 4))
    (PUTCELLSHEET "Sheet1" (COLUMN+N STARTING_CELL 5) (SINGLE_ELE_LIST DETAILS_TO_PRINT 5))
)



(DEFUN C:IMPORT_SPAN_LENGTHS_FROM_OFFSETS ( / )
(PROMPT "SELECT OFFSETS (OFFSET COLOUR CODE : GREEN->SINGLE CANTILEVER YELLOW->DOUBLE CANTILEVER")
(SETQ OFFSET_ENTITIES1 (SSGET))
(SETQ STARTING_OFFSET (CAR (ENTSEL "\nSELECT STARTING OFFSET:")))
(SETQ TRACK_ENTITY (CAR(ENTSEL "\nSELECT TRACK ALIGNMENT:")))
(SETQ STARTING_CELL (GETSTRING "\nENTER STARTING CELL:"))
(SETQ OS_MODE (GETVAR "OSMODE"))
(SETQ 3DOS_MODE (GETVAR "3DOSMODE"))
(SETVAR "OSMODE" 0)
(SETVAR "3DOSMODE" 0)
(COMMAND "UCS" "W")
(SETQ SNAP_POINTS (GET_OFFSET_INTERSECTION_POINTS OFFSET_ENTITIES1 TRACK_ENTITY))
(SETQ SNAP_POINTS_SPAN (SPAN_FROM_OFFSETS_SPECIAL TRACK_ENTITY (SORT_ENTITIES_ALONG_CURVE TRACK_ENTITY SNAP_POINTS (ASSOC STARTING_OFFSET SNAP_POINTS) 1 1) 1))
(PUTCELLSHEET "Sheet1" (COLUMN+N STARTING_CELL 0) (SINGLE_ELE_LIST SNAP_POINTS_SPAN 2))
(PUTCELLSHEET "Sheet1" (COLUMN+N STARTING_CELL 1) (SINGLE_ELE_LIST SNAP_POINTS_SPAN 3))
)


(DEFUN SORT_ENTITIES_ALONG_CURVE (POLYLINE_ENTITY LIST1 STARTING_ENTITY FLAG1 FLAG2 / I TEMP_ELE1 TEMP_ELE2 FINAL_LIST)
   (SETQ I 0 TEMP_ELE1 NIL TEMP_ELE2 NIL FINAL_LIST NIL)
   (WHILE (< I (LENGTH LIST1))
     (SETQ TEMP_ELE1 (DISTANCE_ON_CURVE_GPS POLYLINE_ENTITY (NTH FLAG1 (NTH I LIST1)) (NTH FLAG2 STARTING_ENTITY)))
     (SETQ TEMP_ELE2 (LIST TEMP_ELE1 (NTH I LIST1)))
     (SETQ FINAL_LIST (CONS TEMP_ELE2 FINAL_LIST))
     (SETQ I (+ I 1))
   )
   (SINGLE_ELE_LIST (SORT_FUN FINAL_LIST 0 0) 1)
 )


(DEFUN SPAN_FROM_OFFSETS_SPECIAL (TRACK_CENTER INTERSECTION_POINT FLAG / I TEMP_SPAN FINAL_LIST)
  (SETQ I 0 TEMP_SPAN NIL FINAL_LIST NIL)
  (WHILE (< I (LENGTH INTERSECTION_POINT))
    (IF (/= I (- (LENGTH INTERSECTION_POINT) 1)) (SETQ TEMP_SPAN (RTOS (APPROXIMATE_SPAN (DISTANCE_ON_CURVE_GPS TRACK_CENTER (NTH FLAG (NTH I INTERSECTION_POINT)) (NTH FLAG (NTH (+ I 1) INTERSECTION_POINT))) 0.5) 2 2)) (SETQ TEMP_SPAN NIL))
    (SETQ COLOUR (CDR (ASSOC 62  (ENTGET (NTH 0 (NTH I INTERSECTION_POINT))))))
    (SETQ FINAL_LIST (CONS (APPEND (NTH I INTERSECTION_POINT) (LIST TEMP_SPAN COLOUR)) FINAL_LIST))
    (SETQ I (+ I 1))
  )
  (REVERSE FINAL_LIST)
)




(DEFUN C:EXTRACT_OFFSETS_FROM_EXCEL ( / POLYLINE_ENTITY COPY_ENTITY POINT1 POINT2 START_CELL END_CELL SPANLIST)
    (COMMAND "UCS" "W")
    (SETQ OS_MODE (GETVAR "OSMODE"))
  (SETVAR "OSMODE" 0)
  (SETQ POLYLINE_ENTITY (CAR(ENTSEL "\n SELECT TRACK REFERENCE")))
  (SETQ COPY_ENTITY (CAR(ENTSEL "\n SELECT OBJECT FOR OFFSET")))
  (SETQ POINT1 (GETPOINT "\n PICK STARTING POINT ON CURVE"))
  (SETQ POINT2 (GETPOINT "\n PICK ANY POINT ON CURVE IN REQUIRED DIRECTION"))
  (SETQ START_CELL (GETSTRING "\n ENTER STARTING CELL IN EXCEL"))
  (SETQ END_CELL (GETSTRING "\n ENTER STARTING CELL IN EXCEL"))
  ;(OPENEXCEL (FINDFILE "SPANEXTRACT.XLSX") "Sheet1" T)
  (SETQ SPANLIST (getCellsrow/column "Sheet1" (STRCAT (COLUMN+N START_CELL 0) ":" (COLUMN+N END_CELL 0))))
  (SETQ COLOURLIST (CDR (getCellsrow/column "Sheet1" (STRCAT (COLUMN+N START_CELL 1) ":" (COLUMN+N END_CELL 1)))))
  (OFFSETS_COLOR  POLYLINE_ENTITY COPY_ENTITY POINT1 POINT2 SPANLIST COLOURLIST)
    (SETVAR "OSMODE" OS_MODE)
  (COMMAND "UCS" "P")
)

(DEFUN OFFSETS_COLOR (POLYLINE_ENTITY COPY_ENTITY POINT1 POINT2 SPAN_LIST COLOURLIST /  OS_MODE DIRECTION TEMP_DISTANCE I TEMP_ELE DIST DIRECTION NEXT_POINT TEMP_ELE )

  (SETQ DIRECTION (FIND_DIRECTION POLYLINE_ENTITY POINT1 POINT2))
  (SETQ TEMP_DISTANCE (VLAX-CURVE-GETDISTATPOINT POLYLINE_ENTITY POINT1))
  (SETQ I 0 TEMP_ELE NIL DIST 0)
  (WHILE (< I (LENGTH SPAN_LIST))
    (SETQ DIST (NTH I SPAN_LIST))
    (IF (/= DIST NIL)
    (PROGN
    (IF (= DIRECTION "POSITIVE")
      (SETQ TEMP_DISTANCE (- TEMP_DISTANCE DIST))
      (SETQ TEMP_DISTANCE (+ TEMP_DISTANCE DIST))
    )
    (SETQ NEXT_POINT (VLAX-CURVE-GETPOINTATDIST POLYLINE_ENTITY TEMP_DISTANCE))
    (SETQ TEMP_ELE (COPY_ORTHOGONAL POLYLINE_ENTITY COPY_ENTITY POINT1 NEXT_POINT TEMP_DISTANCE))
    (VLAX-PUT-PROPERTY (VLAX-ENAME->VLA-OBJECT (ENTLAST)) 'COLOR (NTH I COLOURLIST))
    (SETQ COPY_ENTITY (NTH 0 TEMP_ELE) POINT1 (NTH 1 TEMP_ELE))
    )
    )
    (SETQ I (+ I 1))
  )

)




(DEFUN C:UPDATE_DFCC_TC ( / BLOCKS_LIST MAST_TTC_DIR ENT_LIST DFCC_TRACK_CENTER IR_TRACK_CENTER I MAST ROTATION INSERTION_POINT PROJECTION_POINT1 PROJECTION_POINT2 FINAL_INSERTION_POINT)
  ;(SETQ ENT_LIST (FORM_SSSET (SSGET)))
  (SETQ BLOCKS_LIST (FORM_SSSET (SSGET "X" (LIST (CONS 0 "INSERT")))))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ ENT_LIST (SINGLE_ELE_LIST (FILTER_LIST '("UP" "DN") MAST_TTC_DIR 1) 0))
  
(SETQ DFCC_TRACK_CENTER (CAR(ENTSEL "\n SELECT DFCC DN LINE TRACK CENTER:")))
(SETQ IR_TRACK_CENTER (CAR(ENTSEL "\n SELECT DFCC UP LINE TRACK CENTER:")))
(SETQ DFCC_TRACK_CENTER (VLAX-ENAME->VLA-OBJECT DFCC_TRACK_CENTER))
(SETQ IR_TRACK_CENTER (VLAX-ENAME->VLA-OBJECT IR_TRACK_CENTER))
(SETQ I 0 MAST NIL ROTATION NIL INSERTION_POINT NIL PROJECTION_POINT1 NIL PROJECTION_POINT2 NIL FINAL_INSERTION_POINT NIL)
(WHILE (< I (LENGTH ENT_LIST))
  (SETQ MAST (VLAX-ENAME->VLA-OBJECT (NTH I ENT_LIST)))
  (SETQ ROTATION (VLAX-GET-PROPERTY MAST 'ROTATION))
  (SETQ INSERTION_POINT (VLAX-SAFEARRAY->LIST (VLAX-VARIANT-VALUE (VLAX-GET-PROPERTY MAST 'INSERTIONPOINT))))
  (SETQ PROJECTION_POINT1 (VLAX-CURVE-GETCLOSESTPOINTTO DFCC_TRACK_CENTER INSERTION_POINT T))
  (SETQ PROJECTION_POINT2 (VLAX-CURVE-GETCLOSESTPOINTTO IR_TRACK_CENTER INSERTION_POINT T))
  (MODIFY_ATTRIBUTES (NTH I ENT_LIST) (LIST "TC1") (LIST (STRCAT "TC=" (RTOS (DISTANCE2D PROJECTION_POINT1 PROJECTION_POINT2) 2 2))))
  (SETQ I (+ I 1))
)
)



(DEFUN C:UPDATE_DFCC_CHAINAGES ( / WPT1 WPT2 BLOCKS_LIST TRACK_ENTITY_UPTRACK STARTING_POINT ST_CH BLOCK_NAME_LIST MAST_TTC_DIR MAST_UP MAST_DN TOTAL_LIST I )
  (SETQ WPT1 (GETPOINT "\nSELECT POINT1:"))
  (SETQ WPT2 (GETPOINT "\nSELECT POINT2:"))
  (SETQ BLOCKS_LIST (FORM_SSSET (SSGET "W" WPT1 WPT2 (LIST (CONS 0 "INSERT")))))
  (SETQ TRACK_ENTITY_UPTRACK (ENTSEL "\nSELECT TRACK ALIGNMENT FOR UP TRACK (DN LINE):"))
  (SETQ STARTING_POINT (GETPOINT "\nPICK STARTING POINT"))
  (SETQ ST_CH (GETSTRING "\nENTER START CHAINAGE (FORMAT : KM/CHAINAGE):"))
  (SETQ REF_MAST_DN (CAR (ENTSEL "\nSELECT REFERENCE MAST DNLINE:")))
  (SETQ REF_MAST_UP (CAR (ENTSEL "\nSELECT REFERENCE MAST UPLINE:")))
  (SETQ BLOCK_NAME_LIST (EXTRACT_ENTITY_INFO2 BLOCKS_LIST))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_UP (FILTER_LIST '("UP") MAST_TTC_DIR 1))
  (SETQ MAST_DN (FILTER_LIST '("DN") MAST_TTC_DIR 1))
  (SETQ TOTAL_LIST (SINGLE_ELE_LIST (APPEND MAST_UP MAST_DN) 0))
  
  
  (SETQ MAST_UP (SORT_ENTITIES_ALONG_CURVE1 (VLAX-ENAME->VLA-OBJECT (NTH 0 TRACK_ENTITY_UPTRACK)) MAST_UP (LIST 1 STARTING_POINT) 0 1))
  (SETQ MAST_DN (SORT_ENTITIES_ALONG_CURVE1 (VLAX-ENAME->VLA-OBJECT (NTH 0 TRACK_ENTITY_UPTRACK)) MAST_DN (LIST 1 STARTING_POINT) 0 1))
  (UPDATE_CTN_CHAINAGES_GPS ST_CH (SINGLE_ELE_LIST MAST_UP 0))
  (UPDATE_CTN_CHAINAGES_GPS ST_CH (SINGLE_ELE_LIST MAST_DN 0))
  (MATCH_POSITION REF_MAST_UP (SINGLE_ELE_LIST MAST_UP 0))
  (MATCH_POSITION REF_MAST_DN (SINGLE_ELE_LIST MAST_DN 0))
)


 (DEFUN UPDATE_CTN_CHAINAGES_GPS (ST_CH ENT_LIST / I SSSET LOC_NO ST_CH LOC_NUM_LIST ENT_LIST FINAL_LIST BS_PT BS_PT1 ENT_INFO VALUES VALUES1 VALUES2 VALUES3 VALUES4 FDN_REFERENCE FDN_REFERENCE_X FDN_REFERENCE_Y RD_REFERENCE RD_REFERENCE_X RD_REFERENCE_Y TC_REFERENCE TC_REFERENCE_X TC_REFERENCE_Y SPAN_REFERENCE_X SPAN_REFERENCE_Y ENT_LIST_SPAN POINT POINT1 POINT2 POINT3 ENT_LIST_SPAN VISIBILITY_SPAN VISIBILITY_TC VISIBILITY_FDN VISIBILITY_RD I LOC CH TEMP_ELE SCALE POINT_FDN POINT_RD POINT_TC TEMP_SPAN)

  (SETQ	KM_NO (SUBSTR ST_CH 1 (VL-STRING-POSITION (ASCII "/") ST_CH)))

  (SETQ	ST_CH	(SUBSTR	ST_CH (+ (VL-STRING-POSITION (ASCII "/") ST_CH) 2)))
  ;(SETQ LOC_NUM_LIST (SINGLE_ELE_LIST ENT_LIST 1))
  (SETQ TEMP_ELE  ENT_LIST)

  (SETQ I 0 FINAL_LIST NIL CH NIL)

  (WHILE (< I (LENGTH TEMP_ELE))

    (SETQ CH (STRCAT KM_NO "/" ST_CH))

    (MODIFY_ATTRIBUTES (NTH I TEMP_ELE) (LIST "CHAINAGE2") (LIST CH))

    (SETQ TEMP_SPAN (ATOF (NTH 0 (SINGLE_ELE_LIST (EXTRACT_ATTRIBUTES (NTH I TEMP_ELE) (LIST "SPAN1" ) 1) 1))))
    
    (IF (= TEMP_SPAN 0) (PROGN (SETQ I (LENGTH ENT_LIST))))
								      
    (SETQ ST_CH (RTOS (+ (ATOF ST_CH) TEMP_SPAN) 2 2))
    (IF (> (ATOF ST_CH) 1000) (PROGN (SETQ ST_CH (RTOS (- (ATOF ST_CH) 1000) 2 2)) (SETQ KM_NO (RTOS (+ (ATOF KM_NO) 1) 2 0))))
    (SETQ I (+ I 1))
  )
  
)



(DEFUN MATCH_POSITION (ENTNAME ENT_LIST / ENTNAME SSSET ENT_LIST ENT_INFO MAST_NUMBER MAST_NUMBER_X MAST_NUMBER_Y FDN_REFERENCE FDN_REFERENCE_X FDN_REFERENCE_Y RD_REFERENCE RD_REFERENCE_X RD_REFERENCE_Y TC_REFERENCE TC_REFERENCE_X TC_REFERENCE_Y SPAN_REFERENCE_X SPAN_REFERENCE_Y BS_PT VALUES VALUES1 VALUES2 VALUES3 VALUES4 VALUES5 POINT POINT1 POINT2 POINT3 POINT4 POINT5 VISIBILITY_SPAN VISIBILITY_TC VISIBILITY_FDN VISIBILITY_RD I BASE_POINT TEMP_SPAN) 

  (COMMAND "UCS" "W")
  
  (SETQ ENT_LIST (EXTRACT_ENTITY_INFO ENT_LIST 1 3))
  (SETQ ENT_LIST (SORT_FUN ENT_LIST 1 0))
  (SETQ ENT_LIST (SINGLE_ELE_LIST ENT_LIST 0))

  (SETQ DFCC_CTN_CHAINAGE_REFERENCE (GET_TEXT_ALIGNMENT_POINT (LIST ENTNAME) "CHAINAGE2" 0))
  (SETQ DFCC_CTN_CHAINAGE_REFERENCE_X (- (NTH 0 (NTH 1 (NTH 0 DFCC_CTN_CHAINAGE_REFERENCE))) (NTH 0 (CDR (ASSOC 10 (ENTGET ENTNAME))))))
  (SETQ DFCC_CTN_CHAINAGE_REFERENCE_Y (- (NTH 1 (NTH 1 (NTH 0 DFCC_CTN_CHAINAGE_REFERENCE))) (NTH 1 (CDR (ASSOC 10 (ENTGET ENTNAME))))))

  (SETQ REFERENCE_LIST1 (LIST (LIST DFCC_CTN_CHAINAGE_REFERENCE_X DFCC_CTN_CHAINAGE_REFERENCE_Y 0.0)))
  ;(SETQ BS_PT (CDR (ASSOC 10 (ENTGET ENTNAME))))

  (SETQ BASE_ROTATION (VLAX-GET-PROPERTY (VLAX-ENAME->VLA-OBJECT ENTNAME) 'ROTATION))

  (SETQ I 0 BASE_POINT NIL ROTATION NIL TEMP_IMPLANTATION NIL TEMP_POINT_LIST NIL )
  (WHILE (< I (LENGTH ENT_LIST))
    
    (SETQ BASE_POINT (CDR (ASSOC 10 (ENTGET (NTH I ENT_LIST)))))
    (SETQ ROTATION (VLAX-GET-PROPERTY (VLAX-ENAME->VLA-OBJECT (NTH I ENT_LIST)) 'ROTATION))
    (SETQ TEMP_IMPLANTATION (ATOF (NTH 0 (SINGLE_ELE_LIST (EXTRACT_ATTRIBUTES (NTH I ENT_LIST) (LIST "IMPLANTATION1" ) 1) 1))))
    
    (SETQ TEMP_POINT_LIST1 (TRANSFORM_ADJ REFERENCE_LIST1 BASE_POINT (-  ROTATION BASE_ROTATION) (- 3.00 3.00)))

    (CHANGE_TEXT_ALIGNMENT_POINT (NTH I ENT_LIST) '("CHAINAGE2") (LIST (NTH 0 TEMP_POINT_LIST1)))

    (SETQ I (+ I 1))
  )
  (COMMAND "UCS" "P")
  )



(DEFUN C:HIDE_ATTRIBUTES ( / BLOCKS_LIST FLAG FLAG1 ATTR_TAG MAST_TTC_DIR MAST_UP MAST_DN)
  (SETQ BLOCKS_LIST (FORM_SSSET (SSGET "X" (LIST (CONS 0 "INSERT")))))
  (SETQ FLAG (GETSTRING "N\VISIBLE OR INVISIBLE ??? VISIBLE -> 1 INVISIBLE ->0"))
  (SETQ FLAG1 (GETINT "N\UPLINE OR DNLINE OR BOTH??? DNLINE -> 0 UPLINE ->1 BOTH -> 2"))
  (SETQ ATTR_TAG (GETSTRING "ENTER ATTRIBUTE TAGNAME"))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_UP (SINGLE_ELE_LIST (FILTER_LIST '("UP") MAST_TTC_DIR 1) 0))
  (SETQ MAST_DN (SINGLE_ELE_LIST (FILTER_LIST '("DN") MAST_TTC_DIR 1) 0))
  (IF (= FLAG1 0)
    (invis_all_fun MAST_DN FLAG ATTR_TAG)
  )
  (IF (= FLAG1 1)
    (invis_all_fun MAST_UP FLAG ATTR_TAG)
  )
 (IF (= FLAG1 2)
    (invis_all_fun (APPEND MAST_DN MAST_UP) FLAG ATTR_TAG)
  )
)





(defun invis_all_fun ( LIST1 FLAG ATTR_TAG / LIST1 FLAG)
  (vl-load-com)
    (SETQ I 0)
  (while (< I (LENGTH LIST1))
      (CHANGE_VISIBILITY (NTH I LIST1) (LIST ATTR_TAG) (LIST FLAG))
      (SETQ  I (+ I 1)))
 (princ)
)



(DEFUN C:UPDATE_TOTAL_SPANS_GPS ( / BLOCKS_LIST MAST_TTC_DIR MAST_LIST_DNLINE MAST_LIST_UPLINE)
  
  (SETQ TRACK_ENTITY_UPTRACK (CAR(ENTSEL "\nSELECT TRACK ALIGNMENT FOR UP TRACK (DN LINE):")))
  (SETQ STARTING_MAST (CAR(ENTSEL "\nSELECT STARTING_MAST:")))
  (SETQ STARTING_POINT (GETPOINT "\nENTER STARTING POINT FOR UP TRACK (DN LINE):"))
       
  (SETQ BLOCKS_LIST (FORM_SSSET (SSGET "X" (LIST (CONS 0 "INSERT")))))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_LIST_DNLINE (SINGLE_ELE_LIST (FILTER_LIST '("DN") MAST_TTC_DIR 1) 0))
  (SETQ MAST_LIST_UPLINE (SINGLE_ELE_LIST (FILTER_LIST '("UP") MAST_TTC_DIR 1) 0))
  (SETQ MAST_LIST_DNLINE (SORT_FUN (ENTITY_DFX MAST_LIST_DNLINE 10 -1) 1 0))
  (SETQ MAST_LIST_UPLINE (SORT_FUN (ENTITY_DFX MAST_LIST_UPLINE 10 -1) 1 0))
  
  (SETQ MAST_LIST_DNLINE (COMBINE_LIST_ELEMENTS (GET_PROJECTION_FROM_POINT_LIST_FINAL TRACK_ENTITY_UPTRACK (BUILD_LIST MAST_LIST_DNLINE (LIST 0 1)) 1)))
  (SETQ MAST_LIST_UPLINE (COMBINE_LIST_ELEMENTS (GET_PROJECTION_FROM_POINT_LIST_FINAL TRACK_ENTITY_UPTRACK (BUILD_LIST MAST_LIST_UPLINE (LIST 0 1)) 1)))
  
  (SETQ MAST_LIST_DNLINE (SORT_ENTITIES_ALONG_CURVE TRACK_ENTITY_UPTRACK MAST_LIST_DNLINE (LIST 1 STARTING_POINT) 2 1))
  (SETQ MAST_LIST_UPLINE (SORT_ENTITIES_ALONG_CURVE TRACK_ENTITY_UPTRACK MAST_LIST_UPLINE (LIST 1 STARTING_POINT) 2 1))
  (UPDATE_TOTAL_SPANS_GPS1 STARTING_MAST TRACK_ENTITY_UPTRACK (SINGLE_ELE_LIST MAST_LIST_DNLINE 0))
  (UPDATE_TOTAL_SPANS_GPS1 STARTING_MAST TRACK_ENTITY_UPTRACK (SINGLE_ELE_LIST MAST_LIST_UPLINE 0))
  
)

(DEFUN UPDATE_TOTAL_SPANS_GPS1 ( STARTING_MAST TRACK_CENTER MAST_LIST  / SSSET STARTING_MAST TRACK_CENTER ENT_LIST PROJECTTION_POINTS )

   (COMMAND "UCS" "W")
   (SETQ ENT_LIST SSSET)
   (SETQ ENT_LIST (EXTRACT_ENTITY_INFO ENT_LIST 1 3))
   (SETQ ENT_LIST (SORT_MASTS ENT_LIST STARTING_MAST))
   (SETQ PROJECTTION_POINTS (SINGLE_ELE_LIST (GET_PROJECTION_FROM_POINT_LIST_FINAL TRACK_CENTER ENT_LIST 1) 1))
   (UPDATE_SPAN_GPS  TRACK_CENTER  (SINGLE_ELE_LIST ENT_LIST 0) PROJECTTION_POINTS)
   (COMMAND "UCS" "P")
  
)



(DEFUN UPDATE_TOTAL_CHAINAGES_SPLIT_GPS (KM_LIST UPLIST DNLIST POLYLINE_ENTITY / I TEMP_ELE1 TEMP_ELE2 TEMP_ELE3 F LOC_NO ST_CH ENT_LIST TEMP_KM ST_CH_UP ST_CH_DN)
     (SETQ F 0 TEMP_ELE1 NIL TEMP_ELE2 NIL TEMP_ELE3 NIL TEMP_KM NIL)
   (setq dcl_id (load_dialog "DISPLAY_INFO.dcl"))
   (new_dialog "DISPLAY_INFO" dcl_id)
  (WHILE (< F (LENGTH KM_LIST))
    (SETQ TEMP_ELE1 (NTH F KM_LIST) TEMP_ELE2 (NTH F UPLIST) TEMP_ELE3 (NTH F DNLIST) TEMP_ELE4 (NTH (+ F 1) KM_LIST))
     (SET_TILE "INFO" (STRCAT "UPDATING KM " (ITOA (+ F 1)) " OF "  (ITOA (LENGTH KM_LIST))))
     (SET_TILE "PERCENTAGE" (STRCAT (RTOS (/ (* (+ F 1) 100) (ATOF (RTOS (LENGTH KM_LIST) 2 2)) ) 2 2) "%" "COMPLETED"))
    (IF (= F (- (LENGTH KM_LIST) 1))
      (PROGN
      (SET_TILE "INFO" (STRCAT "ALL " "KILOMETER" " LOCATIONS ARE UPDATED SUCESSFULLY"))
      (SET_TILE "PERCENTAGE" "PRESS OK TO CONTINUE")
      )
    )
    
    (SETQ ATTR_LIST (GET_ATTRIBUTES (NTH 0 TEMP_ELE1)))
    (SETQ TEMP_KM (NTH 1 (ASSOC "KM" ATTR_LIST)))
    (SETQ TEMP_KM (SUBSTR TEMP_KM (+ (VL-STRING-POSITION (ASCII ":") TEMP_KM) 2)))

    (IF (/= TEMP_ELE4 NIL)
    (PROGN
    (SETQ ATTR_LIST1 (GET_ATTRIBUTES (NTH 0 TEMP_ELE4)))
    (SETQ TEMP_KM1 (NTH 1 (ASSOC "KM" ATTR_LIST1)))
    (SETQ TEMP_KM1 (SUBSTR TEMP_KM1 (+ (VL-STRING-POSITION (ASCII ":") TEMP_KM1) 2)))
    )
    )
    
    ;(SETQ TEMP_ELE2 (SORT_MASTS_NEW TEMP_ELE2 TEMP_ELE1 1 2))
    ;(SETQ TEMP_ELE3 (SORT_MASTS_NEW TEMP_ELE3 TEMP_ELE1 1 2))
    ;(SETQ LOC_NO (STRCAT (NTH 0 TEMP_ELE1) "/" STARTING_LOCATION))
    ;(VLAX-CURVE-GETCLOSESTPOINTTO POLYLINE_ENTITY (NTH 1 (NTH 0 TEMP_ELE3)) T)
    (IF (= F 0)
    (PROGN
    (SETQ ST_CH_UP (STRCAT TEMP_KM "/" (RTOS (DISTANCE_ON_CURVE_GPS  POLYLINE_ENTITY (NTH 2 TEMP_ELE1) (NTH 1 (NTH 0 TEMP_ELE2))) 2 2)))
    (SETQ ST_CH_DN (STRCAT TEMP_KM "/" (RTOS (DISTANCE_ON_CURVE_GPS  POLYLINE_ENTITY (NTH 2 TEMP_ELE1) (NTH 1 (NTH 0 TEMP_ELE3))) 2 2)))
    )
    )
    
    (SETQ TEMP_ELE2 (UPDATE_CHAINAGES_SPLIT_GPS ST_CH_UP TEMP_ELE2 "DN"))
    (SETQ TEMP_ELE3 (UPDATE_CHAINAGES_SPLIT_GPS ST_CH_DN TEMP_ELE3 "UP"))
    (SETQ END_CH_UP (NTH 0 (NTH 1 (NTH (- (LENGTH TEMP_ELE2) 1) TEMP_ELE2))) END_SPAN_UP (NTH 2 (NTH 1 (NTH (- (LENGTH TEMP_ELE2) 1) TEMP_ELE2))))
    (SETQ END_CH_DN (NTH 0 (NTH 1 (NTH (- (LENGTH TEMP_ELE3) 1) TEMP_ELE3))) END_SPAN_DN (NTH 2 (NTH 1 (NTH (- (LENGTH TEMP_ELE3) 1) TEMP_ELE3))))
    (SETQ ST_CH_UP  (- END_SPAN_UP (- 1000 END_CH_UP)))
    (SETQ ST_CH_DN  (- END_SPAN_DN (- 1000 END_CH_DN)))
    (IF (/= TEMP_ELE4 NIL)
    (PROGN
    (SETQ ST_CH_UP (STRCAT TEMP_KM1 "/" (RTOS ST_CH_UP 2 2)))
    (SETQ ST_CH_DN (STRCAT TEMP_KM1 "/" (RTOS ST_CH_DN 2 2)))
    )
    )
    (SETQ TEMP_MAIN_LIST (ASSIGN_LOCATION_NUMBERS (SORT_MULTILEVEL (APPEND (ADD_LISTS TEMP_ELE2 (N_ELE_LIST "DN" (LENGTH TEMP_ELE2))) (ADD_LISTS TEMP_ELE3 (N_ELE_LIST "UP" (LENGTH TEMP_ELE3)))) 1 0 1)))
    (UPDATE_LOC_NUMBERS_GPS TEMP_MAIN_LIST TEMP_KM)
    (SETQ F (+ F 1))
  )
  (setq ddiag(start_dialog))
)


(DEFUN C:UPDATE_TOTAL_CHAINAGES_GPS ( / )

  (SETQ WPT1 (GETPOINT "\nSELECT POINT1:"))
  (SETQ WPT2 (GETPOINT "\nSELECT POINT2:"))
  (SETQ BLOCKS_LIST (FORM_SSSET (SSGET "W" WPT1 WPT2 (LIST (CONS 0 "INSERT")))))
  (SETQ TRACK_ENTITY_UPTRACK (ENTSEL "\nSELECT TRACK ALIGNMENT FOR UP TRACK (DN LINE):"))
  (SETQ STARTING_POINT (GETPOINT "\nPICK STARTING POINT"))
  (SETQ BLOCK_NAME_LIST (EXTRACT_ENTITY_INFO2 BLOCKS_LIST))
  (SETQ KM_STONE_LIST (FILTER_LIST (LIST "KM_NEW" "KM_STONE" "KMNEW" "KMSTONE") BLOCK_NAME_LIST 1))
  (SETQ KM_STONE_LIST (SORT_FUN (ENTITY_DFX (SINGLE_ELE_LIST KM_STONE_LIST 0) 10 -1) 1 0))
  (SETQ KM_STONE_COORDINATES (COMBINE_LIST_ELEMENTS (GET_PROJECTION_FROM_POINT_LIST_FINAL (NTH 0 TRACK_ENTITY_UPTRACK) (BUILD_LIST KM_STONE_LIST (LIST 0 1)) 1)))
  (SETQ KM_STONE_COORDINATES (SORT_ENTITIES_ALONG_CURVE (NTH 0 TRACK_ENTITY_UPTRACK) KM_STONE_COORDINATES (LIST 1 STARTING_POINT) 2 1))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_UP (FILTER_LIST '("UP") MAST_TTC_DIR 1))
  (SETQ MAST_DN (FILTER_LIST '("DN") MAST_TTC_DIR 1))

  (SETQ MAST_UP (ATTRIBUTES_FROM_ENTITIES (SINGLE_ELE_LIST MAST_UP 0) "SPAN1" 0))
  (SETQ MAST_DN (ATTRIBUTES_FROM_ENTITIES (SINGLE_ELE_LIST MAST_DN 0) "SPAN1" 0))

  (SETQ DNLINE_MASTS (BUILD_LIST (ADD_LISTS MAST_UP (ENTITY_DFX (SINGLE_ELE_LIST MAST_UP 0) 10 -1)) (LIST 0 3 1)))
  (SETQ UPLINE_MASTS (BUILD_LIST (ADD_LISTS MAST_DN (ENTITY_DFX (SINGLE_ELE_LIST MAST_DN 0) 10 -1)) (LIST 0 3 1)))
 
  (SETQ UPLINE_MAST_ENTITIES (BUILD_LIST (COMBINE_LIST_ELEMENTS (GET_PROJECTION_FROM_POINT_LIST_FINAL (NTH 0 TRACK_ENTITY_UPTRACK) (ADD_LISTS UPLINE_MASTS (N_ELE_LIST "DN" (LENGTH UPLINE_MASTS))) 1)) (LIST 0 4 2 3)))
  (SETQ DNLINE_MAST_ENTITIES (BUILD_LIST (COMBINE_LIST_ELEMENTS (GET_PROJECTION_FROM_POINT_LIST_FINAL (NTH 0 TRACK_ENTITY_UPTRACK) (ADD_LISTS DNLINE_MASTS (N_ELE_LIST "UP" (LENGTH DNLINE_MASTS))) 1)) (LIST 0 4 2 3)))
  
  (SETQ UPLINE_MASTS (FIND_IN_BETWEEN_GPS KM_STONE_COORDINATES UPLINE_MAST_ENTITIES (NTH 0 TRACK_ENTITY_UPTRACK) 2 1 (NTH 0 KM_STONE_COORDINATES)))
  (SETQ DNLINE_MASTS (FIND_IN_BETWEEN_GPS KM_STONE_COORDINATES DNLINE_MAST_ENTITIES (NTH 0 TRACK_ENTITY_UPTRACK) 2 1 (NTH 0 KM_STONE_COORDINATES)))
  (UPDATE_TOTAL_CHAINAGES_SPLIT_GPS  (VL-REMOVE (NTH (- (LENGTH KM_STONE_COORDINATES) 1) KM_STONE_COORDINATES) KM_STONE_COORDINATES) (SINGLE_ELE_LIST (SORT_ENTITIES_ALONG_CURVE1 (NTH 0 TRACK_ENTITY_UPTRACK) UPLINE_MASTS (NTH 0 KM_STONE_COORDINATES) 1 2) 0) (SINGLE_ELE_LIST (SORT_ENTITIES_ALONG_CURVE1 (NTH 0 TRACK_ENTITY_UPTRACK) DNLINE_MASTS (NTH 0 KM_STONE_COORDINATES) 1 2) 0) (NTH 0 TRACK_ENTITY_UPTRACK))


)



(DEFUN C:UPDATE_TOTAL_CHAINAGES_GPS2 ( / )

  (SETQ WPT1 (GETPOINT "\nSELECT POINT1:"))
  (SETQ WPT2 (GETPOINT "\nSELECT POINT2:"))
  (SETQ ST_CH_DN (GETSTRING "\nENTER STARTING CHAINAGE OF DNLINE"))
  (SETQ ST_CH_UP (GETSTRING "\nENTER STARTING CHAINAGE OF UPLINE"))
  (SETQ BLOCKS_LIST (FORM_SSSET (SSGET "W" WPT1 WPT2 (LIST (CONS 0 "INSERT")))))
  (SETQ TRACK_ENTITY_UPTRACK (ENTSEL "\nSELECT TRACK ALIGNMENT FOR UP TRACK (DN LINE):"))
  (SETQ STARTING_POINT (GETPOINT "\nPICK STARTING POINT"))
  (SETQ BLOCK_NAME_LIST (EXTRACT_ENTITY_INFO2 BLOCKS_LIST))
  (SETQ KM_STONE_LIST (FILTER_LIST (LIST "KM_NEW" "KM_STONE" "KMNEW" "KMSTONE") BLOCK_NAME_LIST 1))
  (SETQ KM_STONE_LIST (SORT_FUN (ENTITY_DFX (SINGLE_ELE_LIST KM_STONE_LIST 0) 10 -1) 1 0))
  (SETQ KM_STONE_COORDINATES (COMBINE_LIST_ELEMENTS (GET_PROJECTION_FROM_POINT_LIST_FINAL (NTH 0 TRACK_ENTITY_UPTRACK) (BUILD_LIST KM_STONE_LIST (LIST 0 1)) 1)))
  (SETQ KM_STONE_COORDINATES (SORT_ENTITIES_ALONG_CURVE (NTH 0 TRACK_ENTITY_UPTRACK) KM_STONE_COORDINATES (LIST 1 STARTING_POINT) 2 1))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_UP (FILTER_LIST '("UP") MAST_TTC_DIR 1))
  (SETQ MAST_DN (FILTER_LIST '("DN") MAST_TTC_DIR 1))
  (SETQ MAST_UP (ATTRIBUTES_FROM_ENTITIES (SINGLE_ELE_LIST MAST_UP 0) "SPAN1" 0))
  (SETQ MAST_DN (ATTRIBUTES_FROM_ENTITIES (SINGLE_ELE_LIST MAST_DN 0) "SPAN1" 0))

  (SETQ DNLINE_MASTS (BUILD_LIST (ADD_LISTS MAST_UP (ENTITY_DFX (SINGLE_ELE_LIST MAST_UP 0) 10 -1)) (LIST 0 3 1)))
  (SETQ UPLINE_MASTS (BUILD_LIST (ADD_LISTS MAST_DN (ENTITY_DFX (SINGLE_ELE_LIST MAST_DN 0) 10 -1)) (LIST 0 3 1)))
 
  (SETQ UPLINE_MAST_ENTITIES (BUILD_LIST (COMBINE_LIST_ELEMENTS (GET_PROJECTION_FROM_POINT_LIST_FINAL (NTH 0 TRACK_ENTITY_UPTRACK) (ADD_LISTS UPLINE_MASTS (N_ELE_LIST "DN" (LENGTH UPLINE_MASTS))) 1)) (LIST 0 4 2 3)))
  (SETQ DNLINE_MAST_ENTITIES (BUILD_LIST (COMBINE_LIST_ELEMENTS (GET_PROJECTION_FROM_POINT_LIST_FINAL (NTH 0 TRACK_ENTITY_UPTRACK) (ADD_LISTS DNLINE_MASTS (N_ELE_LIST "UP" (LENGTH DNLINE_MASTS))) 1)) (LIST 0 4 2 3)))
  
  (SETQ UPLINE_MASTS (FIND_IN_BETWEEN_GPS KM_STONE_COORDINATES UPLINE_MAST_ENTITIES (NTH 0 TRACK_ENTITY_UPTRACK) 2 1 (NTH 0 KM_STONE_COORDINATES)))
  (SETQ DNLINE_MASTS (FIND_IN_BETWEEN_GPS KM_STONE_COORDINATES DNLINE_MAST_ENTITIES (NTH 0 TRACK_ENTITY_UPTRACK) 2 1 (NTH 0 KM_STONE_COORDINATES)))
  (UPDATE_TOTAL_CHAINAGES_SPLIT_GPS2  (VL-REMOVE (NTH (- (LENGTH KM_STONE_COORDINATES) 1) KM_STONE_COORDINATES) KM_STONE_COORDINATES) (SINGLE_ELE_LIST (SORT_ENTITIES_ALONG_CURVE1 (NTH 0 TRACK_ENTITY_UPTRACK) UPLINE_MASTS (NTH 0 KM_STONE_COORDINATES) 1 2) 0) (SINGLE_ELE_LIST (SORT_ENTITIES_ALONG_CURVE1 (NTH 0 TRACK_ENTITY_UPTRACK) DNLINE_MASTS (NTH 0 KM_STONE_COORDINATES) 1 2) 0) (NTH 0 TRACK_ENTITY_UPTRACK) ST_CH_DN ST_CH_UP )


)



(DEFUN UPDATE_TOTAL_CHAINAGES_SPLIT_GPS2 (KM_LIST UPLIST DNLIST POLYLINE_ENTITY ST_CH_DN1 ST_CH_UP1 / I TEMP_KM TEMP_KM1 TEMP_ELE1 TEMP_ELE2 TEMP_ELE3 F LOC_NO ST_CH ENT_LIST TEMP_KM ST_CH_UP ST_CH_DN)
     (SETQ F 0 TEMP_ELE1 NIL TEMP_ELE2 NIL TEMP_ELE3 NIL TEMP_KM NIL)
   (setq dcl_id (load_dialog "DISPLAY_INFO.dcl"))
   (new_dialog "DISPLAY_INFO" dcl_id)
  (WHILE (< F (LENGTH KM_LIST))
    (SETQ TEMP_ELE1 (NTH F KM_LIST) TEMP_ELE2 (NTH F UPLIST) TEMP_ELE3 (NTH F DNLIST) TEMP_ELE4 (NTH (+ F 1) KM_LIST))
    (SET_TILE "INFO" (STRCAT "UPDATING KM " (ITOA (+ F 1)) " OF "  (ITOA (LENGTH KM_LIST))))
     (SET_TILE "PERCENTAGE" (STRCAT (RTOS (/ (* (+ F 1) 100) (ATOF (RTOS (LENGTH KM_LIST) 2 2)) ) 2 2) "%" "COMPLETED"))
    (IF (= F (- (LENGTH KM_LIST) 1))
      (PROGN
      (SET_TILE "INFO" (STRCAT "ALL " "KILOMETER" " LOCATIONS ARE UPDATED SUCESSFULLY"))
      (SET_TILE "PERCENTAGE" "PRESS OK TO CONTINUE")
      )
    )
    
    (SETQ ATTR_LIST (GET_ATTRIBUTES (NTH 0 TEMP_ELE1)))
    (SETQ TEMP_KM (NTH 1 (ASSOC "KM" ATTR_LIST)))
    (SETQ TEMP_KM (SUBSTR TEMP_KM (+ (VL-STRING-POSITION (ASCII ":") TEMP_KM) 2)))

    (IF (/= TEMP_ELE4 NIL)
    (PROGN
    (SETQ ATTR_LIST1 (GET_ATTRIBUTES (NTH 0 TEMP_ELE4)))
    (SETQ TEMP_KM1 (NTH 1 (ASSOC "KM" ATTR_LIST1)))
    (SETQ TEMP_KM1 (SUBSTR TEMP_KM1 (+ (VL-STRING-POSITION (ASCII ":") TEMP_KM1) 2)))
    )
    )
    
    ;(SETQ TEMP_ELE2 (SORT_MASTS_NEW TEMP_ELE2 TEMP_ELE1 1 2))
    ;(SETQ TEMP_ELE3 (SORT_MASTS_NEW TEMP_ELE3 TEMP_ELE1 1 2))
    ;(SETQ LOC_NO (STRCAT (NTH 0 TEMP_ELE1) "/" STARTING_LOCATION))
    ;(VLAX-CURVE-GETCLOSESTPOINTTO POLYLINE_ENTITY (NTH 1 (NTH 0 TEMP_ELE3)) T)
    (IF (= F 0)
    (PROGN
    (SETQ ST_CH_UP (STRCAT TEMP_KM "/"  ST_CH_DN1))
    (SETQ ST_CH_DN (STRCAT TEMP_KM "/" ST_CH_UP1))
    )
    )
    
    (SETQ TEMP_ELE2 (UPDATE_CHAINAGES_SPLIT_GPS ST_CH_UP TEMP_ELE2 "DN"))
    (SETQ TEMP_ELE3 (UPDATE_CHAINAGES_SPLIT_GPS ST_CH_DN TEMP_ELE3 "UP"))
    (SETQ END_CH_UP (NTH 0 (NTH 1 (NTH (- (LENGTH TEMP_ELE2) 1) TEMP_ELE2))) END_SPAN_UP (NTH 2 (NTH 1 (NTH (- (LENGTH TEMP_ELE2) 1) TEMP_ELE2))))
    (SETQ END_CH_DN (NTH 0 (NTH 1 (NTH (- (LENGTH TEMP_ELE3) 1) TEMP_ELE3))) END_SPAN_DN (NTH 2 (NTH 1 (NTH (- (LENGTH TEMP_ELE3) 1) TEMP_ELE3))))
    (SETQ ST_CH_UP  (- END_SPAN_UP (- 1000 END_CH_UP)))
    (SETQ ST_CH_DN  (- END_SPAN_DN (- 1000 END_CH_DN)))
    (IF (/= TEMP_ELE4 NIL)
    (PROGN
    (SETQ ST_CH_UP (STRCAT TEMP_KM1 "/" (RTOS ST_CH_UP 2 2)))
    (SETQ ST_CH_DN (STRCAT TEMP_KM1 "/" (RTOS ST_CH_DN 2 2)))
    )
    )
    (SETQ TEMP_MAIN_LIST (ASSIGN_LOCATION_NUMBERS (SORT_MULTILEVEL (APPEND (ADD_LISTS TEMP_ELE2 (N_ELE_LIST "DN" (LENGTH TEMP_ELE2))) (ADD_LISTS TEMP_ELE3 (N_ELE_LIST "UP" (LENGTH TEMP_ELE3)))) 1 0 1)))
    (UPDATE_LOC_NUMBERS_GPS TEMP_MAIN_LIST TEMP_KM)
    (SETQ F (+ F 1))
  )
  (setq ddiag(start_dialog))
)



(DEFUN C:GET_OFFSET_DISTANCE ( / BLOCKS_LIST MAST_TTC_DIR ENT_LIST DFCC_TRACK_CENTER IR_TRACK_CENTER I MAST ROTATION INSERTION_POINT PROJECTION_POINT1 PROJECTION_POINT2 FINAL_INSERTION_POINT)
;(SETQ ENT_LIST (FORM_SSSET (SSGET)))
(SETQ START_CHAINAGE (GETREAL "\n ENTER START CHAINAGE:"))
  
  (SETQ START_POINT (GETPOINT "\n PICK STARTING POINT ON DFCC LINE"))
  (SETQ POINT2 (GETPOINT "\n PICK ANY POINT ON CURVE IN REQUIRED DIRECTION"))

  
  
  
(SETQ DFCC_TRACK_CENTER (CAR(ENTSEL "\n SELECT DFCC TRACK CENTER:")))

(SETQ IR_TRACK_CENTER (CAR(ENTSEL "\n SELECT IR TRACK CENTER:")))
(SETQ DFCC_TRACK_CENTER (VLAX-ENAME->VLA-OBJECT DFCC_TRACK_CENTER))
(SETQ IR_TRACK_CENTER (VLAX-ENAME->VLA-OBJECT IR_TRACK_CENTER))

(SETQ DIST (VLAX-CURVE-GETDISTATPOINT DFCC_TRACK_CENTER START_POINT))
(SETQ DIRECTION (FIND_DIRECTION DFCC_TRACK_CENTER START_POINT POINT2))
(SETQ I 0 MAST NIL ROTATION NIL INSERTION_POINT NIL PROJECTION_POINT1 NIL PROJECTION_POINT2 NIL FINAL_INSERTION_POINT NIL FINAL_LIST NIL)
(WHILE (/= (VLAX-CURVE-GETPOINTATDIST DFCC_TRACK_CENTER DIST) NIL)

  (SETQ PROJECTION_POINT1 (VLAX-CURVE-GETCLOSESTPOINTTO DFCC_TRACK_CENTER START_POINT T))
  (SETQ PROJECTION_POINT2 (VLAX-CURVE-GETCLOSESTPOINTTO IR_TRACK_CENTER START_POINT T))
  (SETQ FINAL_LIST (CONS (LIST START_CHAINAGE (RTOS (DISTANCE2D PROJECTION_POINT1 PROJECTION_POINT2) 2 2)) FINAL_LIST))
  (SETQ START_CHAINAGE (+ START_CHAINAGE 20))
  
  (SETQ I (+ I 1))
  

(IF (= DIRECTION "POSITIVE")
      (SETQ DIST (- DIST 20))
      (SETQ DIST (+ DIST 20))
)
  (SETQ START_POINT (VLAX-CURVE-GETPOINTATDIST DFCC_TRACK_CENTER DIST))
)
(SETQ FINAL_LIST (REVERSE FINAL_LIST))
(PUTCELLSHEET "Sheet1" (COLUMN+N "A2" 0) (SINGLE_ELE_LIST FINAL_LIST 0))
(PUTCELLSHEET "Sheet1" (COLUMN+N "A2" 1) (SINGLE_ELE_LIST FINAL_LIST 1))
)


(DEFUN C:PRINT_EMBANKMENT_DETAILS ( / BLOCKS_LIST TRACK_FLAG MAST_TTC_DIR ENT_LIST DFCC_TRACK_CENTER IR_TRACK_CENTER I MAST ROTATION INSERTION_POINT PROJECTION_POINT1 PROJECTION_POINT2 PROJECTION_POINT3 PROJECTION_POINT4 FINAL_INSERTION_POINT LOC_NO  CHAINAGE IMPLANTATION TEMP_KM TEMP_CHAINAGE TEMP_LIST FINAL_LIST)
;(SETQ ENT_LIST (FORM_SSSET (SSGET)))
  (SETQ START_CELL (GETSTRING "\n ENTER START CELL IN THE EXCEL SHEET:"))
  (SETQ BLOCKS_LIST (FORM_SSSET (SSGET "X" (LIST (CONS 0 "INSERT")))))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ TRACK_FLAG (GETSTRING "\n FOR WHICH TRACK YOU WANT???, TYPE UP OR DN:"))
  (SETQ ENT_LIST (SINGLE_ELE_LIST (FILTER_LIST (LIST TRACK_FLAG) MAST_TTC_DIR 1) 0))

(SETQ DFCC_DN_TRACK_CENTER (CAR(ENTSEL "\n SELECT DFCC DN LINE TRACK CENTER:")))
(SETQ DFCC_UP_TRACK_CENTER (CAR(ENTSEL "\n SELECT DFCC UP LINE TRACK CENTER:")))
;(SETQ IR_TRACK_CENTER (CAR(ENTSEL "\n SELECT IR TRACK CENTER:")))
(SETQ FORMATION_DN (CAR(ENTSEL "\n SELECT DN TRACK FORMATION:")))
(SETQ FORMATION_UP (CAR(ENTSEL "\n SELECT UP TRACK FORMATION:")))
(SETQ DFCC_DN_TRACK_CENTER (VLAX-ENAME->VLA-OBJECT DFCC_DN_TRACK_CENTER))
(SETQ DFCC_UP_TRACK_CENTER (VLAX-ENAME->VLA-OBJECT DFCC_UP_TRACK_CENTER))
;(SETQ IR_TRACK_CENTER (VLAX-ENAME->VLA-OBJECT IR_TRACK_CENTER))
(SETQ FORMATION_DN (VLAX-ENAME->VLA-OBJECT FORMATION_DN))
(SETQ FORMATION_UP (VLAX-ENAME->VLA-OBJECT FORMATION_UP))
(SETQ I 0 MAST NIL ROTATION NIL INSERTION_POINT NIL PROJECTION_POINT1 NIL PROJECTION_POINT2 NIL PROJECTION_POINT3 NIL PROJECTION_POINT4 NIL FINAL_INSERTION_POINT NIL LOC_NO NIL CHAINAGE NIL IMPLANTATION NIL TEMP_KM NIL TEMP_CHAINAGE NIL TEMP_LIST NIL FINAL_LIST NIL)
(WHILE (< I (LENGTH ENT_LIST))
  (SETQ MAST (VLAX-ENAME->VLA-OBJECT (NTH I ENT_LIST)))
  
  (SETQ INSERTION_POINT (VLAX-SAFEARRAY->LIST (VLAX-VARIANT-VALUE (VLAX-GET-PROPERTY MAST 'INSERTIONPOINT))))
  (SETQ PROJECTION_POINT1 (VLAX-CURVE-GETCLOSESTPOINTTO DFCC_DN_TRACK_CENTER INSERTION_POINT T))
  (SETQ PROJECTION_POINT2 (VLAX-CURVE-GETCLOSESTPOINTTO DFCC_UP_TRACK_CENTER INSERTION_POINT T))
  (SETQ PROJECTION_POINT3 (VLAX-CURVE-GETCLOSESTPOINTTO FORMATION_DN INSERTION_POINT T))
  (SETQ PROJECTION_POINT4 (VLAX-CURVE-GETCLOSESTPOINTTO FORMATION_UP INSERTION_POINT T))
  (SETQ LOC_NO (NTH 0 (SINGLE_ELE_LIST (EXTRACT_ATTRIBUTES (NTH I ENT_LIST) (LIST "MAST_NUMBER1" ) 1) 1)))
  (SETQ CHAINAGE (NTH 0 (SINGLE_ELE_LIST (EXTRACT_ATTRIBUTES (NTH I ENT_LIST) (LIST "CHAINAGE2" ) 1) 1)))
  (SETQ IMPLANTATION (NTH 0 (SINGLE_ELE_LIST (EXTRACT_ATTRIBUTES (NTH I ENT_LIST) (LIST "IMPLANTATION1" ) 1) 1)))
  (SETQ	TEMP_KM (SUBSTR CHAINAGE 1 (VL-STRING-POSITION (ASCII "/") CHAINAGE)))
  (SETQ	TEMP_CHAINAGE (SUBSTR CHAINAGE (+ (VL-STRING-POSITION (ASCII "/") CHAINAGE) 2)))
  (SETQ CHAINAGE (+ (* (ATOF TEMP_KM) 1000) (* (ATOF TEMP_CHAINAGE) 1)))
  (SETQ CHAINAGE (RTOS CHAINAGE 2 2))
  (SETQ TEMP_LIST (LIST LOC_NO CHAINAGE IMPLANTATION (DISTANCE2D PROJECTION_POINT1 PROJECTION_POINT2) (IF (= TRACK_FLAG "DN") (DISTANCE2D PROJECTION_POINT1 PROJECTION_POINT3) (DISTANCE2D PROJECTION_POINT2 PROJECTION_POINT4)) (DISTANCE2D PROJECTION_POINT3 PROJECTION_POINT4)))
  
  (SETQ FINAL_LIST (CONS TEMP_LIST FINAL_LIST))
  (SETQ I (+ I 1))
)
  (SETQ FINAL_LIST (REVERSE FINAL_LIST))
  (PUTCELLSHEET "Sheet1" (COLUMN+N START_CELL 0) (SINGLE_ELE_LIST FINAL_LIST 0))
  (PUTCELLSHEET "Sheet1" (COLUMN+N START_CELL 1) (SINGLE_ELE_LIST FINAL_LIST 1))
  (PUTCELLSHEET "Sheet1" (COLUMN+N START_CELL 2) (SINGLE_ELE_LIST FINAL_LIST 2))
  (PUTCELLSHEET "Sheet1" (COLUMN+N START_CELL 3) (SINGLE_ELE_LIST FINAL_LIST 3))
  (PUTCELLSHEET "Sheet1" (COLUMN+N START_CELL 4) (SINGLE_ELE_LIST FINAL_LIST 4))
  (PUTCELLSHEET "Sheet1" (COLUMN+N START_CELL 5) (SINGLE_ELE_LIST FINAL_LIST 5))
)



(DEFUN C:GET_EMBANKMENT_PROFILE ( / BLOCKS_LIST MAST_TTC_DIR ENT_LIST DFCC_TRACK_CENTER IR_TRACK_CENTER I MAST ROTATION INSERTION_POINT PROJECTION_POINT1 PROJECTION_POINT2 FINAL_INSERTION_POINT)
;(SETQ ENT_LIST (FORM_SSSET (SSGET)))
(SETQ START_CHAINAGE (GETREAL "\n ENTER START CHAINAGE:"))
  
  (SETQ START_POINT (GETPOINT "\n PICK STARTING POINT ON DFCC LINE"))
  (SETQ POINT2 (GETPOINT "\n PICK ANY POINT ON CURVE IN REQUIRED DIRECTION"))

  
  
  
(SETQ DFCC_TRACK_CENTER_DN (CAR(ENTSEL "\n SELECT DFCC TRACK CENTER (DN MAIN):")))
(SETQ DFCC_TRACK_CENTER_UP (CAR(ENTSEL "\n SELECT DFCC TRACK CENTER (UP MAIN):")))
(SETQ FORMATION_END_DN (CAR(ENTSEL "\n SELECT FORMATION TOP END (DN MAIN):")))
(SETQ FORMATION_END_UP (CAR(ENTSEL "\n SELECT FORMATION TOP END (UP MAIN):")))
(SETQ DFCC_TRACK_CENTER_DN (VLAX-ENAME->VLA-OBJECT DFCC_TRACK_CENTER_DN))
(SETQ DFCC_TRACK_CENTER_UP (VLAX-ENAME->VLA-OBJECT DFCC_TRACK_CENTER_UP))
(SETQ FORMATION_END_DN (VLAX-ENAME->VLA-OBJECT FORMATION_END_DN))
(SETQ FORMATION_END_UP (VLAX-ENAME->VLA-OBJECT FORMATION_END_UP))


(SETQ DIST (VLAX-CURVE-GETDISTATPOINT DFCC_TRACK_CENTER_DN START_POINT))
(SETQ DIRECTION (FIND_DIRECTION DFCC_TRACK_CENTER_DN START_POINT POINT2))
(SETQ I 0 MAST NIL ROTATION NIL INSERTION_POINT NIL PROJECTION_POINT1 NIL PROJECTION_POINT2 NIL FINAL_INSERTION_POINT NIL FINAL_LIST (LIST (LIST "CHAINAGE" "FORMATION END (DN MAIN)" "FORMATION END (UP MAIN)" "TRACK CENTER")))
(WHILE (/= (VLAX-CURVE-GETPOINTATDIST DFCC_TRACK_CENTER_DN DIST) NIL)

  (SETQ PROJECTION_POINT_DN (VLAX-CURVE-GETCLOSESTPOINTTO DFCC_TRACK_CENTER_DN START_POINT T))
  (SETQ PROJECTION_POINT_UP (VLAX-CURVE-GETCLOSESTPOINTTO DFCC_TRACK_CENTER_UP START_POINT T))
  (SETQ FORMATION_PROJECTION_POINT_DN (VLAX-CURVE-GETCLOSESTPOINTTO FORMATION_END_DN START_POINT T))
  (SETQ FORMATION_PROJECTION_POINT_UP (VLAX-CURVE-GETCLOSESTPOINTTO FORMATION_END_UP START_POINT T))
  (SETQ FINAL_LIST (CONS (LIST START_CHAINAGE (RTOS (DISTANCE2D PROJECTION_POINT_DN FORMATION_PROJECTION_POINT_DN) 2 2) (RTOS (DISTANCE2D PROJECTION_POINT_UP FORMATION_PROJECTION_POINT_UP) 2 2) (RTOS (DISTANCE2D PROJECTION_POINT_DN PROJECTION_POINT_UP) 2 2) ) FINAL_LIST))
  (SETQ START_CHAINAGE (+ START_CHAINAGE 20))
  
  (SETQ I (+ I 1))
  

(IF (= DIRECTION "POSITIVE")
      (SETQ DIST (- DIST 20))
      (SETQ DIST (+ DIST 20))
)
  (SETQ START_POINT (VLAX-CURVE-GETPOINTATDIST DFCC_TRACK_CENTER_DN DIST))
)
(SETQ FINAL_LIST (REVERSE FINAL_LIST))
(PUTCELLSHEET "Sheet1" (COLUMN+N "A2" 0) (SINGLE_ELE_LIST FINAL_LIST 0))
(PUTCELLSHEET "Sheet1" (COLUMN+N "A2" 1) (SINGLE_ELE_LIST FINAL_LIST 1))
(PUTCELLSHEET "Sheet1" (COLUMN+N "A2" 2) (SINGLE_ELE_LIST FINAL_LIST 2))
(PUTCELLSHEET "Sheet1" (COLUMN+N "A2" 3) (SINGLE_ELE_LIST FINAL_LIST 3))
)



(DEFUN C:100KM_PEGS ( / )
  (SETQ POINT1 (GETPOINT "\n PICK STARTING POINT"))
  (SETQ POINT2 (GETPOINT "\n PICK ANY POINT ON CURVE IN REQUIRED DIRECTION "))
  (SETQ DFCC_CHAINAGE (GETREAL "\nSELECT DFCC CHAINAGE (REAL NUMBER) :"))
  (SETQ CONT_CHAINAGE (GETREAL "\nSELECT CONT CHAINAGE (REAL NUMBER) :"))
  (SETQ REFERENCE_POLYLINE (CAR(ENTSEL "\nSELECT REFERENCE TRACK ALIGNMENT:")))
  (SETQ DIRECTION (FIND_DIRECTION REFERENCE_POLYLINE POINT1 POINT2))
  (SETQ I 0 TEMP_POINT POINT1 TEMP_SLOPE (NTH 1 (POINT_SLOPE_AT_INTERVAL POINT1 REFERENCE_POLYLINE DIRECTION 0)))
  (SETQ TEMP_DFCC_CHAINAGE (STRCAT (RTOS (FIX (/ DFCC_CHAINAGE 1000)) 2 0) "/" (RTOS (- DFCC_CHAINAGE (* (FIX (/ DFCC_CHAINAGE 1000)) 1000)) 2 2)))
  (SETQ TEMP_CONT_CHAINAGE (STRCAT (RTOS (FIX (/ CONT_CHAINAGE 1000)) 2 0) "/" (RTOS (- CONT_CHAINAGE (* (FIX (/ CONT_CHAINAGE 1000)) 1000)) 2 2)))
(WHILE (/= TEMP_POINT NIL)

(COMMAND "INSERT" "OHE-100-PEG-MARKS" TEMP_POINT  "1" (* (/ 180 PI) TEMP_SLOPE))
(MODIFY_ATTRIBUTES (ENTLAST) (LIST "DFCC_CHAINAGE" "CONTINUOUS_CHAINAGE") (LIST TEMP_DFCC_CHAINAGE TEMP_CONT_CHAINAGE))
(SETQ INSERTION_INFO (POINT_SLOPE_AT_INTERVAL TEMP_POINT REFERENCE_POLYLINE DIRECTION 100))
(SETQ TEMP_POINT (NTH 0 INSERTION_INFO))
(SETQ TEMP_SLOPE (NTH 1 INSERTION_INFO))
(SETQ DFCC_CHAINAGE (+ DFCC_CHAINAGE 100))
(SETQ CONT_CHAINAGE (+ CONT_CHAINAGE 100))
(SETQ TEMP_DFCC_CHAINAGE (STRCAT (RTOS (FIX (/ DFCC_CHAINAGE 1000)) 2 0) "/" (RTOS (- DFCC_CHAINAGE (* (FIX (/ DFCC_CHAINAGE 1000)) 1000)) 2 2)))
(SETQ TEMP_CONT_CHAINAGE (STRCAT (RTOS (FIX (/ CONT_CHAINAGE 1000)) 2 0) "/" (RTOS (- CONT_CHAINAGE (* (FIX (/ CONT_CHAINAGE 1000)) 1000)) 2 2)))
)
)



(DEFUN C:20KM_PEGS ( / )
  (SETQ POINT1 (GETPOINT "\n PICK STARTING POINT"))
  (SETQ POINT2 (GETPOINT "\n PICK ANY POINT ON CURVE IN REQUIRED DIRECTION "))
  (SETQ REFERENCE_POLYLINE (CAR(ENTSEL "\nSELECT REFERENCE TRACK ALIGNMENT:")))
  (SETQ DIRECTION (FIND_DIRECTION REFERENCE_POLYLINE POINT1 POINT2))
  (SETQ I 0 TEMP_POINT POINT1 TEMP_SLOPE (NTH 1 (POINT_SLOPE_AT_INTERVAL POINT1 REFERENCE_POLYLINE DIRECTION 0)))
(WHILE (/= TEMP_POINT NIL)
(COMMAND "INSERT" "OHE-20-PEG-MARKS" TEMP_POINT  "1" (* (/ 180 PI) TEMP_SLOPE ))
(SETQ INSERTION_INFO (POINT_SLOPE_AT_INTERVAL TEMP_POINT REFERENCE_POLYLINE DIRECTION 20))
(SETQ TEMP_POINT (NTH 0 INSERTION_INFO))
(SETQ TEMP_SLOPE (NTH 1 INSERTION_INFO))
)
)







  
(DEFUN POINT_SLOPE_AT_INTERVAL ( START_POINT REFERENCE_POLYLINE DIRECTION INTERVAL / MAIN_POINT ANGLE1 DERIVATIVE SLOPE)
  (SETQ  TEMP_DISTANCE NIL MAIN_POINT NIL ANGLE1 NIL DERIVATIVE NIL SLOPE NIL)
  (SETQ TEMP_DISTANCE (VLAX-CURVE-GETDISTATPOINT REFERENCE_POLYLINE START_POINT))
    (IF (= DIRECTION "POSITIVE")
      (SETQ TEMP_DISTANCE (- TEMP_DISTANCE INTERVAL))
      (SETQ TEMP_DISTANCE (+ TEMP_DISTANCE INTERVAL))
    )
  
  (SETQ MAIN_POINT (VLAX-CURVE-GETPOINTATDIST REFERENCE_POLYLINE TEMP_DISTANCE))
  (IF (/= MAIN_POINT NIL)
  (PROGN
  (SETQ ANGLE1 (VLAX-CURVE-GETPARAMATPOINT REFERENCE_POLYLINE MAIN_POINT))
  (SETQ DERIVATIVE (VLAX-CURVE-GETFIRSTDERIV REFERENCE_POLYLINE ANGLE1))
  (SETQ SLOPE (ANGLE '(0 0 0) DERIVATIVE))
  )
  )
  (LIST MAIN_POINT SLOPE)

)



(DEFUN C:UPDATE_CHAINAGES_SPECIAL ( / SSSET LOC_NO ST_CH ENT_LIST BS_PT ENT_INFO VALUES VALUES1 VALUES2 VALUES3 VALUES4 FDN_REFERENCE FDN_REFERENCE_X FDN_REFERENCE_Y RD_REFERENCE RD_REFERENCE_X RD_REFERENCE_Y TC_REFERENCE TC_REFERENCE_X TC_REFERENCE_Y SPAN_REFERENCE_X SPAN_REFERENCE_Y ENT_LIST_SPAN POINT POINT1 POINT2 POINT3 ENT_LIST_SPAN VISIBILITY_SPAN VISIBILITY_TC VISIBILITY_FDN VISIBILITY_RD I LOC CH TEMP_ELE SCALE POINT_FDN POINT_RD POINT_TC TEMP_SPAN)
  (PROMPT "\n SELECT MASTS")
  (SETQ SSSET (SSGET))
  (SETQ SCALE (GETREAL "\n ENTER SCALE : "))
  (SETQ LOC_NO (GETSTRING "\n ENTER STARTING MAST LOCATION NUMBER :"))
  (SETQ ST_CH (GETSTRING "\n ENTER STARTING MAST CHAINAGE :"))
  (SETQ	KM_NO (SUBSTR LOC_NO 1 (VL-STRING-POSITION (ASCII "/") LOC_NO)))
  (SETQ	LOC_NO	(SUBSTR	LOC_NO (+ (VL-STRING-POSITION (ASCII "/") LOC_NO) 2)))
  (SETQ	ST_CH	(SUBSTR	ST_CH (+ (VL-STRING-POSITION (ASCII "/") ST_CH) 2)))
  
  (SETQ ENT_LIST (SINGLE_ELE_LIST (FILTER_LIST (LIST "SINGLE_CANT_MAST" "DOUBLE_CANT_MAST" "TRIPLE_CANT_MAST") (EXTRACT_ENTITY_INFO2 (FORM_SSSET SSSET)) 1) 0))
  (SETQ ENT_LIST (EXTRACT_ENTITY_INFO ENT_LIST 1 3))
  (SETQ ENT_LIST (SORT_FUN ENT_LIST 1 0))
  (SETQ ENT_LIST (SINGLE_ELE_LIST ENT_LIST 0))
  
  (SETQ ENT_LIST_SPAN (ATTRIBUTES_FROM_ENTITIES ENT_LIST "SPAN1" 0))
  (SETQ I 0)
   (setq dcl_id (load_dialog "DISPLAY_INFO.dcl"))
   (new_dialog "DISPLAY_INFO" dcl_id)
  (WHILE (< I (LENGTH ENT_LIST_SPAN))
    (SETQ LOC (STRCAT KM_NO "/" LOC_NO))
    (SETQ CH (STRCAT KM_NO "/" ST_CH))
     (SET_TILE "INFO" (STRCAT "UPDATING LOC NO "  LOC " " "OF "  (ITOA I)))
     (SET_TILE "PERCENTAGE" (STRCAT "UPDATING CHAINAGE " CH))
    (IF (= I (- (LENGTH ENT_LIST_SPAN) 1))
      (PROGN
      (SET_TILE "INFO" (STRCAT "ALL "  (ITOA (+ I 1)) " LOCATIONS ARE UPDATED SUCESSFULLY"))
      (SET_TILE "PERCENTAGE" "PRESS OK TO VIEW RESULTS")
      )
    )
    
    (SETQ TEMP_ELE  (NTH I ENT_LIST_SPAN))
    (SETQ BASE_POINT (CDR (ASSOC 10 (ENTGET (NTH 0 TEMP_ELE)))))
    (MODIFY_ATTRIBUTES (NTH 0 TEMP_ELE) (LIST "MAST_NUMBER1" "CHAINAGE1") (LIST LOC CH))
 
    
    (SETQ TEMP_SPAN (* (ATOF (NTH 1 TEMP_ELE)) SCALE))
    (IF (/= TEMP_SPAN 0)
    (PROGN

    )
    (PROGN
      (IF (/= I (- (LENGTH ENT_LIST_SPAN) 1)) (PROGN (SET_TILE "INFO" (STRCAT "SPAN HAS NOT BEEN ENTERED IN LOC NO "  LOC   ))
     (SET_TILE "PERCENTAGE" (STRCAT "PROGRAM STOPPED AT CHAINAGE " CH " PLEASE CHECK..."))))
      (SETQ I (LENGTH ENT_LIST_SPAN))
    ))
    (SETQ LOC_NO (ITOA (+ (ATOI LOC_NO) 2)))
    (SETQ ST_CH (RTOS (+ (ATOF ST_CH) (ATOF (NTH 1 TEMP_ELE))) 2 2))
    (SETQ I (+ I 1))
    )(setq ddiag(start_dialog))
)
