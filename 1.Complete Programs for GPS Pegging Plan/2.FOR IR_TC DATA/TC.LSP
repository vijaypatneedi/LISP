(DEFUN GET_CO-ORDINATES ( ENT_LIST  / ENT_LIST I TEMP_CHAINAGE TEMP_EFFNAME TEMP_SPAN FINAL_LIST)

  (SETQ I 0 TEMP_CHAINAGE NIL TEMP_EFFNAME NIL TEMP_SPAN NIL FINAL_LIST NIL)
  (WHILE (< I (LENGTH ENT_LIST))
    (SETQ TEMP_NUMBER (NTH 0 (SINGLE_ELE_LIST (EXTRACT_ATTRIBUTES (NTH I ENT_LIST) (LIST "MAST_NUMBER1" ) 1) 1)))
    (SETQ TEMP_CHAINAGE (NTH 0 (SINGLE_ELE_LIST (EXTRACT_ATTRIBUTES (NTH I ENT_LIST) (LIST "CHAINAGE1" ) 1) 1)))
    (SETQ TEMP_EFFNAME (VLAX-GET-PROPERTY (VLAX-ENAME->VLA-OBJECT (NTH I ENT_LIST)) 'EFFECTIVENAME))
    (SETQ TEMP_MAST_TYPE (NTH 0 (SINGLE_ELE_LIST (EXTRACT_ATTRIBUTES (NTH I ENT_LIST) (LIST "MAST_TYPE1" ) 1) 1)))
    (SETQ TEMP_SPAN (NTH 0 (SINGLE_ELE_LIST (EXTRACT_ATTRIBUTES (NTH I ENT_LIST) (LIST "SPAN1" ) 1) 1)))
    (SETQ TEMP_CO-ORDINATES (CDR (ASSOC 10 (ENTGET (NTH I ENT_LIST)))))
    (SETQ FINAL_LIST (CONS (APPEND (LIST TEMP_NUMBER TEMP_CHAINAGE TEMP_EFFNAME TEMP_MAST_TYPE TEMP_SPAN) TEMP_CO-ORDINATES) FINAL_LIST))
    (SETQ I (+ I 1))
  )
  (REVERSE FINAL_LIST)
  
)

(DEFUN C:PRINT_TC_DATA ( / )
  (SETQ BLOCKS_LIST (FORM_SSSET (SSGET "X" (LIST (CONS 0 "INSERT")))))
  (SETQ TRACK_ENTITY_UPTRACK (CAR(ENTSEL "\nSELECT TRACK ALIGNMENT FOR UP TRACK (DN LINE):")))
  (SETQ TRACK_ENTITY_DNTRACK (CAR(ENTSEL "\nSELECT TRACK ALIGNMENT FOR DN TRACK (UP LINE):")))
  (SETQ STARTING_POINT (GETPOINT "\nENTER STARTING POINT FOR UP TRACK (DN LINE):"))
  (SETQ STARTING_POINT_DN (GETPOINT "\nENTER STARTING POINT FOR DN TRACK (UP LINE):"))
  (SETQ STARTING_CELL (GETSTRING "\nEnter starting cell"))
  (SETQ BLOCK_NAME_LIST (EXTRACT_ENTITY_INFO2 BLOCKS_LIST))
  (SETQ TC_LIST (FILTER_LIST (LIST "IR_TC_BLOCK") BLOCK_NAME_LIST 1))
  (SETQ TC_LIST (BUILD_LIST (ENTITY_DFX (SINGLE_ELE_LIST TC_LIST 0) 10 -1) (LIST 0 1)))
  (SETQ STRUCTURE_LIST (YARD_DATA_COLLECT_GPS BLOCKS_LIST '("SINGLE_CANT_MAST" "DOUBLE_CANT_MAST" "TRIPLE_CANT_MAST" "TTC" "PORTAL" "SS0" "SS1" "SS2" "SS3" "SS4" "SS5") 1 3))
  (IF (/= TC_LIST NIL) (SETQ ANCHOR_START_STRUCTURE_MAP_DATA (DATA_TO_STRUCTURE_MAP1 TC_LIST STRUCTURE_LIST 1 1)) (SETQ ANCHOR_START_STRUCTURE_MAP_DATA NIL))
  (SETQ TC_LIST (SINGLE_ELE_LIST ANCHOR_START_STRUCTURE_MAP_DATA 0))
  (SETQ STRUCTURE_LIST (SINGLE_ELE_LIST ANCHOR_START_STRUCTURE_MAP_DATA 1))
  (SETQ DETAILS_TO_PRINT (GET_CO-ORDINATES STRUCTURE_LIST))
  (SETQ I 0 FINAL_TC_LIST NIL)
  (WHILE (< I (LENGTH ANCHOR_START_STRUCTURE_MAP_DATA))
  (SETQ TEMP_NUMBER (NTH 0 (SINGLE_ELE_LIST (EXTRACT_ATTRIBUTES (NTH 0 (NTH I ANCHOR_START_STRUCTURE_MAP_DATA)) (LIST "DFCC_IR_TC" ) 1) 1)))
  (SETQ TEMP_LOC (NTH 0 (SINGLE_ELE_LIST (EXTRACT_ATTRIBUTES (NTH 1 (NTH I ANCHOR_START_STRUCTURE_MAP_DATA)) (LIST "MAST_NUMBER1" ) 1) 1)))
  (SETQ TEMP_NUMBER (ATOF (SUBSTR TEMP_NUMBER
		           (+ (VL-STRING-POSITION (ASCII "=") TEMP_NUMBER) 2)
	      ))
  )
  (SETQ FINAL_TC_LIST (CONS (LIST TEMP_LOC TEMP_NUMBER) FINAL_TC_LIST))
  (SETQ I (+ I 1))
  )
  (SETQ FINAL_TC_LIST (REVERSE FINAL_TC_LIST))
  (SETQ I 0 FINAL_TC_LIST1 NIL)
  (WHILE (< I (LENGTH FINAL_TC_LIST))
    (SETQ TEMP_TC (NTH 1 (ASSOC (NTH I (SINGLE_ELE_LIST DETAILS_TO_PRINT 0)) FINAL_TC_LIST)))
    (SETQ FINAL_TC_LIST1 (CONS TEMP_TC FINAL_TC_LIST1))
    (SETQ I (+ I 1))
  )
  (SETQ FINAL_TC_LIST1 (REVERSE FINAL_TC_LIST1))
  (PUTCELLSHEET "Sheet1" (COLUMN+N STARTING_CELL 0) (SINGLE_ELE_LIST DETAILS_TO_PRINT 0))
  (PUTCELLSHEET "Sheet1" (COLUMN+N STARTING_CELL 1) (SINGLE_ELE_LIST DETAILS_TO_PRINT 1))
  (PUTCELLSHEET "Sheet1" (COLUMN+N STARTING_CELL 2) (SINGLE_ELE_LIST DETAILS_TO_PRINT 2))
  (PUTCELLSHEET "Sheet1" (COLUMN+N STARTING_CELL 3) (SINGLE_ELE_LIST DETAILS_TO_PRINT 3))
  (PUTCELLSHEET "Sheet1" (COLUMN+N STARTING_CELL 4) (SINGLE_ELE_LIST DETAILS_TO_PRINT 4))
  (PUTCELLSHEET "Sheet1" (COLUMN+N STARTING_CELL 5) (SINGLE_ELE_LIST DETAILS_TO_PRINT 5))
  (PUTCELLSHEET "Sheet1" (COLUMN+N STARTING_CELL 6) (SINGLE_ELE_LIST DETAILS_TO_PRINT 6))
  (PUTCELLSHEET "Sheet1" (COLUMN+N STARTING_CELL 7) FINAL_TC_LIST1)
)
