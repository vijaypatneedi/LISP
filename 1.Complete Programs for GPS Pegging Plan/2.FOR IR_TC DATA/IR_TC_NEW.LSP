(DEFUN C:UPDATE_IR_TC_NEW ( / BLOCKS_LIST MAST_TTC_DIR ENT_LIST DFCC_TRACK_CENTER IR_TRACK_CENTER I MAST ROTATION INSERTION_POINT PROJECTION_POINT1 PROJECTION_POINT2 FINAL_INSERTION_POINT)
 (SETQ WPT1 (GETPOINT "\nSELECT POINT1:"))
 (SETQ WPT2 (GETPOINT "\nSELECT POINT2:"))
 (SETQ WPT3 (GETPOINT "\nSELECT POINT3:"))
 (SETQ WPT4 (GETPOINT "\nSELECT POINT4:"))
 (SETQ BLOCKS_LIST (FORM_SSSET (SSGET "WP" (LIST WPT1 WPT2 WPT3 WPT4) (LIST (CONS 0 "INSERT")))))
 
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ ENT_LIST (SINGLE_ELE_LIST (FILTER_LIST '("DN") MAST_TTC_DIR 1) 0))
  
(SETQ DFCC_TRACK_CENTER (CAR(ENTSEL "\n SELECT DFCC TRACK CENTER:")))
(SETQ IR_TRACK_CENTER (CAR(ENTSEL "\n SELECT IR TRACK CENTER:")))
(SETQ DFCC_TRACK_CENTER (VLAX-ENAME->VLA-OBJECT DFCC_TRACK_CENTER))
(SETQ IR_TRACK_CENTER (VLAX-ENAME->VLA-OBJECT IR_TRACK_CENTER))
(SETQ I 0 MAST NIL ROTATION NIL INSERTION_POINT NIL PROJECTION_POINT1 NIL PROJECTION_POINT2 NIL FINAL_INSERTION_POINT NIL)
(WHILE (< I (LENGTH ENT_LIST))
  (SETQ MAST (VLAX-ENAME->VLA-OBJECT (NTH I ENT_LIST)))
  (SETQ ROTATION (VLAX-GET-PROPERTY MAST 'ROTATION))
  (SETQ INSERTION_POINT (VLAX-SAFEARRAY->LIST (VLAX-VARIANT-VALUE (VLAX-GET-PROPERTY MAST 'INSERTIONPOINT))))
  (SETQ PROJECTION_POINT1 (VLAX-CURVE-GETCLOSESTPOINTTO DFCC_TRACK_CENTER INSERTION_POINT T))
  (SETQ PROJECTION_POINT2 (VLAX-CURVE-GETCLOSESTPOINTTO IR_TRACK_CENTER INSERTION_POINT T))
  (IF (>= (DISTANCE2D PROJECTION_POINT1 PROJECTION_POINT2) 16)
    (SETQ FINAL_INSERTION_POINT (POLAR PROJECTION_POINT1 (+ (* 1 (/ PI 2)) ROTATION) (/ (DISTANCE2D PROJECTION_POINT1 PROJECTION_POINT2) 2)))
    (SETQ FINAL_INSERTION_POINT (POLAR PROJECTION_POINT1 (+ (* 1 (/ PI 2)) ROTATION) 8.5))
  )
  (COMMAND "INSERT" "IR_TC_BLOCK" FINAL_INSERTION_POINT "1" (* (/ 180 PI) ROTATION) )
  (MODIFY_ATTRIBUTES (ENTLAST) (LIST "DFCC_IR_TC") (LIST (STRCAT "TC=" (RTOS (DISTANCE2D PROJECTION_POINT1 PROJECTION_POINT2) 2 2))))
  (SETQ I (+ I 1))
)
)




(DEFUN C:UPDATE_DRAIN_IMPLANTATION ( / BLOCKS_LIST MAST_TTC_DIR ENT_LIST DFCC_TRACK_CENTER IR_TRACK_CENTER I MAST ROTATION INSERTION_POINT PROJECTION_POINT1 PROJECTION_POINT2 FINAL_INSERTION_POINT)
 (SETQ WPT1 (GETPOINT "\nSELECT POINT1:"))
 (SETQ WPT2 (GETPOINT "\nSELECT POINT2:"))
 (SETQ WPT3 (GETPOINT "\nSELECT POINT3:"))
 (SETQ WPT4 (GETPOINT "\nSELECT POINT4:"))
 
 (SETQ BLOCKS_LIST (FORM_SSSET (SSGET "WP" (LIST WPT1 WPT2 WPT3 WPT4) (LIST (CONS 0 "INSERT")))))
 
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ ENT_LIST (SINGLE_ELE_LIST (FILTER_LIST '("DN") MAST_TTC_DIR 1) 0))
  
(SETQ DFCC_TRACK_CENTER (CAR(ENTSEL "\n SELECT DFCC TRACK CENTER:")))
(SETQ DRAIN_CENTER_LINE(CAR(ENTSEL "\n SELECT DRAIN CENTER LINE:")))
(SETQ DFCC_TRACK_CENTER (VLAX-ENAME->VLA-OBJECT DFCC_TRACK_CENTER))
(SETQ DRAIN_CENTER_LINE (VLAX-ENAME->VLA-OBJECT DRAIN_CENTER_LINE))
(SETQ I 0 MAST NIL ROTATION NIL INSERTION_POINT NIL PROJECTION_POINT1 NIL PROJECTION_POINT2 NIL FINAL_INSERTION_POINT NIL)
(WHILE (< I (LENGTH ENT_LIST))
  (SETQ MAST (VLAX-ENAME->VLA-OBJECT (NTH I ENT_LIST)))
  (SETQ ROTATION (VLAX-GET-PROPERTY MAST 'ROTATION))
  (SETQ INSERTION_POINT (VLAX-SAFEARRAY->LIST (VLAX-VARIANT-VALUE (VLAX-GET-PROPERTY MAST 'INSERTIONPOINT))))
  (SETQ PROJECTION_POINT1 (VLAX-CURVE-GETCLOSESTPOINTTO DFCC_TRACK_CENTER INSERTION_POINT T))
  (SETQ PROJECTION_POINT2 (VLAX-CURVE-GETCLOSESTPOINTTO DRAIN_CENTER_LINE INSERTION_POINT T))
  (IF (>= (DISTANCE2D PROJECTION_POINT1 PROJECTION_POINT2) 16)
    (SETQ FINAL_INSERTION_POINT (POLAR PROJECTION_POINT1 (+ (* 1 (/ PI 2)) ROTATION) (/ (DISTANCE2D PROJECTION_POINT1 PROJECTION_POINT2) 2)))
    (SETQ FINAL_INSERTION_POINT (POLAR PROJECTION_POINT1 (+ (* 1 (/ PI 2)) ROTATION) 10))
  )
  (COMMAND "INSERT" "DRAIN_IMPLANTATION" FINAL_INSERTION_POINT "1" (* (/ 180 PI) ROTATION) )
  (MODIFY_ATTRIBUTES (ENTLAST) (LIST "DRAIN_IMPLANTATION") (LIST (STRCAT "i=" (RTOS (DISTANCE2D PROJECTION_POINT1 PROJECTION_POINT2) 2 2))))
  (SETQ I (+ I 1))
)
)
