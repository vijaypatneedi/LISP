(DEFUN C:107 ( / )
 (SETQ WPT1 (GETPOINT "ENTER STARTING POINT IN LOP"))
 (SETQ WPT2 (GETPOINT "\n ENTER ENDING POINT IN LOP"))
 (SETQ STARTING_CELL (GETSTRING "\nEnter starting cell"))
 (SETQ BLOCKS_LIST (FORM_SSSET (SSGET "W" WPT1 WPT2 (LIST (CONS 0 "INSERT")))))
 (SETQ BLOCK_NAME_LIST (EXTRACT_ENTITY_INFO2 BLOCKS_LIST))
 (SETQ ANCHOR_LIST (FILTER_LIST (LIST "ANCHOR") BLOCK_NAME_LIST 1))
 (SETQ ANCHOR_LIST (ATTRIBUTES_FROM_ENTITIES ANCHOR_LIST "WIRE_SYSTEM" 0))
 (SETQ ANCHOR_LIST (SINGLE_ELE_LIST (FILTER_LIST (LIST "107") ANCHOR_LIST 2) 0))

 (SETQ ANCHOR_LIST_BTB (FILTER_LIST (LIST "BTB_ANC") BLOCK_NAME_LIST 1))
 (SETQ ANCHOR_TYPE1 (ATTRIBUTES_FROM_ENTITIES ANCHOR_LIST_BTB "WIRE_SYSTEM1" 0))
 (SETQ 107_LIST1 (SINGLE_ELE_LIST (FILTER_LIST (LIST "107") ANCHOR_TYPE1 2) 0))

  (SETQ ANCHOR_TYPE2 (ATTRIBUTES_FROM_ENTITIES ANCHOR_LIST_BTB "WIRE_SYSTEM2" 0))
 (SETQ 107_LIST2 (SINGLE_ELE_LIST (FILTER_LIST (LIST "107") ANCHOR_TYPE2 2) 0))
  
 (SETQ ANCHOR_NATURE_LIST (SINGLE_ELE_LIST (ATTRIBUTES_FROM_ENTITIES ANCHOR_LIST "WIRE_RUN1" 0) 1))
 (IF (/= 107_LIST1 NIL) (SETQ ANCHOR_NATURE_LIST1 (SINGLE_ELE_LIST (ATTRIBUTES_FROM_ENTITIES 107_LIST1 "WIRE_NO1" 0) 1)))
 (IF (/= 107_LIST2 NIL) (SETQ ANCHOR_NATURE_LIST2 (SINGLE_ELE_LIST (ATTRIBUTES_FROM_ENTITIES 107_LIST2 "WIRE_NO2" 0) 1)))
 (PUTCELLSHEET "Sheet1" (COLUMN+N STARTING_CELL 0) (APPEND ANCHOR_NATURE_LIST ANCHOR_NATURE_LIST1 ANCHOR_NATURE_LIST2))
)
