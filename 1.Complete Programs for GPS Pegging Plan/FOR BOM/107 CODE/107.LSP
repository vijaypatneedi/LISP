(DEFUN C:107 ( / )
 (SETQ WPT1 (GETPOINT "ENTER STARTING POINT IN LOP"))
 (SETQ WPT2 (GETPOINT "\n ENTER ENDING POINT IN LOP"))
 (SETQ STARTING_CELL (GETSTRING "\nEnter starting cell"))
 (SETQ BLOCKS_LIST (FORM_SSSET (SSGET "W" WPT1 WPT2 (LIST (CONS 0 "INSERT")))))
 (SETQ BLOCK_NAME_LIST (EXTRACT_ENTITY_INFO2 BLOCKS_LIST))
 (SETQ ANCHOR_LIST (FILTER_LIST (LIST "ANCHOR") BLOCK_NAME_LIST 1))
 (SETQ ANCHOR_LIST (ATTRIBUTES_FROM_ENTITIES ANCHOR_LIST "WIRE_SYSTEM" 0))
 (SETQ ANCHOR_LIST (SINGLE_ELE_LIST (FILTER_LIST (LIST "107") ANCHOR_LIST 2) 0))
 (SETQ ANCHOR_NATURE_LIST (SINGLE_ELE_LIST (ATTRIBUTES_FROM_ENTITIES ANCHOR_LIST "WIRE_RUN1" 0) 1))
 (PUTCELLSHEET "Sheet1" (COLUMN+N STARTING_CELL 0) ANCHOR_NATURE_LIST)
)
