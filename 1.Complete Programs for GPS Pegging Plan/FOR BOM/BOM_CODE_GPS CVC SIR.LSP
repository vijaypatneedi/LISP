(DEFUN GET_CANTILEVERS_GPS ( PT NAME_BLK ENAMEBLK / SS_SET I LIST1 ENAME BS_POINT TEMP_ELE LIST1)
(IF (= NAME_BLK "PORTAL" "SS5")
  (SETQ SS_SET (SSGET "F" (GET_BOX_POINTS_PORTAL ENAMEBLK) '((0 . "INSERT"))))
  (SETQ SS_SET (SSGET "F" (BLOCK_REFERENCE_LENGTHS_GPS NAME_BLK ENAMEBLK) '((0 . "INSERT"))))
)
  (SETQ I 0)
  (SETQ ENAME NIL)
  (SETQ BS_POINT NIL)
  (SETQ TEMP_ELE NIL)
  (SETQ LIST1 NIL)
  (IF (/= SS_SET NIL)
(WHILE (< I (SSLENGTH SS_SET))
      (SETQ ENAME (SSNAME SS_SET I))
  (IF (/= ENAME ENAMEBLK)
      (PROGN (SETQ BS_POINT (CDR (ASSOC 10 (ENTGET ENAME))))
      (SETQ TEMP_ELE (APPEND (LIST ENAME) BS_POINT))
      
      
      (SETQ LIST1 (CONS TEMP_ELE LIST1))))
      (SETQ I (+ I 1))
    )
(SETQ LIST1 (REVERSE (SORT_FUN LIST1 0 2)))
    )(SINGLE_ELE_LIST LIST1 0)
)


(DEFUN YARD_STRUCTURE_INFO_GPS (ENT_NAME	 /	      ENTINFO
			    TEMP_ELE1	 TEMP_ELE2    TEMP_ELE3
			    TEMP_ELE4	 FINAL_LIST   EFFNAME
			   )
  (SETQ	TEMP_ELE1 NIL
	TEMP_ELE2 NIL
	TEMP_ELE3 NIL
	TEMP_ELE4 NIL
	TEMP_ELE5 NIL
	TEMP_ELE6 NIL
  )
  (SETQ ENTINFO (ENTGET ENT_NAME))
  (SETQ TEMP_ELE1 (LIST 1 ENT_NAME))
  (SETQ	TEMP_ELE2 (LIST	2
			(VLAX-GET-PROPERTY
			  (VLAX-ENAME->VLA-OBJECT ENT_NAME)
			  "EFFECTIVENAME"
			)
		  )
  )
  (SETQ FLIPLIST (GET_FLIPSTATES_GPS ENT_NAME (NTH 1 TEMP_ELE2)))
  (SETQ TEMP_ELE3 (LIST 3 (CDR (ASSOC 10 ENTINFO))))
  (SETQ	TEMP_ELE4 (LIST	4
			(MERGE_FLIPSTATES
			  (GET_ATTRIBUTES ENT_NAME)
			  (NTH 1 FLIPLIST)
			)
		  )
  )

  (SETQ TEMP_ELE5 (LIST 5 (NTH 0 FLIPLIST)))
  (IF (/= (VL-POSITION (NTH 1 TEMP_ELE2) (LIST "PORTAL" "TTC" "SS5" "SS4")) NIL)

     
    (SETQ TEMP_ELE6
	   (LIST 6
		 (GET_CANTILEVERS_GPS
		   (NTH 1 TEMP_ELE3)
		   (NTH 1 TEMP_ELE2)
		   ENT_NAME
		 )
	   )
    )
    (SETQ TEMP_ELE6 (LIST 6 NIL))
  )
  (SETQ	FINAL_LIST
	 (LIST TEMP_ELE1 TEMP_ELE2 TEMP_ELE3 TEMP_ELE4 TEMP_ELE5
	       TEMP_ELE6)
  )
)






(DEFUN PORTAL_END_POINTS_GPS (LIST1 / I ENAME TEMP_ELE LIST2)
(SETQ I 0)
(SETQ ENAME NIL)
(SETQ TEMP_ELE NIL)
(SETQ LIST2 NIL)
(WHILE (< I (LENGTH LIST1))
(SETQ ENAME (NTH I LIST1))
(SETQ INSERTION_POINT (VLAX-SAFEARRAY->LIST (VLAX-VARIANT-VALUE (VLAX-GET-PROPERTY (VLAX-ENAME->VLA-OBJECT ENAME) 'INSERTIONPOINT))))
(SETQ ROTATION (VLAX-GET-PROPERTY (VLAX-ENAME->VLA-OBJECT ENAME) 'ROTATION))
(SETQ TEMP_ELE  (TRANSFORM (BUILD_LIST (FILTER_LIST '("LINE") (BLOCK_ENAME1 ENAME) 1) '(3 4 5)) INSERTION_POINT ROTATION))
;(SETQ TEMP_ELE  (SUM_LIST (NTH 1 (ASSOC 3 (YARD_STRUCTURE_INFO_GPS ENAME))) (BLOCK_REFERENCE_LENGTHS "PORTAL" ENAME)))
(SETQ TEMP_ELE (LIST (LIST ENAME (NTH 0 TEMP_ELE)) (LIST ENAME (NTH 1 TEMP_ELE))))
(SETQ LIST2 (CONS TEMP_ELE LIST2))
(SETQ I (+ I 1))
)
(REVERSE LIST2)
)




(DEFUN GET_CANTILEVERS_GPS ( PT NAME_BLK ENAMEBLK / SS_SET I LIST1 ENAME BS_POINT TEMP_ELE LIST1)
(SETQ SS_SET (SSGET "F" (BLOCK_REFERENCE_LENGTHS_GPS NAME_BLK ENAMEBLK) '((0 . "INSERT"))))
  (SETQ I 0)
  (SETQ ENAME NIL)
  (SETQ BS_POINT NIL)
  (SETQ TEMP_ELE NIL)
  (SETQ LIST1 NIL)
  (IF (/= SS_SET NIL)
(WHILE (< I (SSLENGTH SS_SET))
      (SETQ ENAME (SSNAME SS_SET I))
  (IF (/= ENAME ENAMEBLK)
      (PROGN (SETQ BS_POINT (CDR (ASSOC 10 (ENTGET ENAME))))
      (SETQ TEMP_ELE (APPEND (LIST ENAME) BS_POINT))
      
      
      (SETQ LIST1 (CONS TEMP_ELE LIST1))))
      (SETQ I (+ I 1))
    )
(SETQ LIST1 (REVERSE (SORT_FUN LIST1 0 2)))
    )(SINGLE_ELE_LIST LIST1 0)
)


(DEFUN BLOCK_REFERENCE_LENGTHS_GPS (BLOCKNAME EBLOCKNAME / BASE_POINT POINTS_LIST I LIST2 TEMP_ELE TEMP_ELE1 J LIST1)

(SETQ INSERTION_POINT (VLAX-SAFEARRAY->LIST (VLAX-VARIANT-VALUE (VLAX-GET-PROPERTY (VLAX-ENAME->VLA-OBJECT EBLOCKNAME) 'INSERTIONPOINT))))
(SETQ ROTATION (VLAX-GET-PROPERTY (VLAX-ENAME->VLA-OBJECT EBLOCKNAME) 'ROTATION))
(SETQ POINTS_LIST (BUILD_LIST (FILTER_LIST '("LINE") (BLOCK_ENAME1 EBLOCKNAME) 1) '(3 4 5)))
(TRANSFORM POINTS_LIST INSERTION_POINT ROTATION)
  
)



(DEFUN SORT_ENTITIES_ALONG_CURVE1 (POLYLINE_ENTITY LIST1 STARTING_ENTITY FLAG1 FLAG2 / I TEMP_ELE1 TEMP_ELE2 FINAL_LIST)
   (SETQ I 0 TEMP_ELE1 NIL TEMP_ELE2 NIL FINAL_LIST NIL)
   (WHILE (< I (LENGTH LIST1))
     (SETQ TEMP_ELE1 (DISTANCE_ON_CURVE_GPS POLYLINE_ENTITY (VLAX-CURVE-GETCLOSESTPOINTTO POLYLINE_ENTITY (CDR (ASSOC 10 (ENTGET (NTH FLAG1 (NTH I LIST1))))) T) (NTH FLAG2 STARTING_ENTITY)))
     (SETQ TEMP_ELE2 (LIST TEMP_ELE1 (NTH I LIST1)))
     (SETQ FINAL_LIST (CONS TEMP_ELE2 FINAL_LIST))
     (SETQ I (+ I 1))
   )
   (SINGLE_ELE_LIST (SORT_FUN FINAL_LIST 0 0) 1)
 )


(DEFUN EXTRACT_UB/SM_INFO_GPS (PORTAL_DATA / I TEMP_ELE LIST1 STRUCTURE_TYPE CANTILEVER_TYPE UB_LIST SM_LIST TEMP_ELE1 LIST2 )
  (SETQ I 0)
  (SETQ TEMP_ELE NIL)
  (SETQ LIST1 NIL)
  (WHILE (< I (LENGTH PORTAL_DATA))
  (SETQ STRUCTURE_TYPE (YARD_STRUCTURE_INFO_GPS (NTH 0 (NTH I PORTAL_DATA))))
  (SETQ CANTILEVER_TYPE (NTH 1 (ASSOC 6 STRUCTURE_TYPE)))
  (SETQ UB_LIST (FILTER_LIST '("UB") (EXTRACT_ENTITY_INFO CANTILEVER_TYPE 1 2) 1))
  (SETQ SM_LIST (SINGLE_ELE_LIST (FILTER_LIST '("SUPER_MAST") (EXTRACT_ENTITY_INFO CANTILEVER_TYPE 1 2) 1) 0))
  (IF (/= UB_LIST NIL)
    (PROGN (SETQ TEMP_ELE (APPEND (LIST (NTH 0 (NTH I PORTAL_DATA))) UB_LIST))
           (SETQ LIST1 (CONS TEMP_ELE LIST1))
    )
  )
  (IF (/= SM_LIST NIL)
    (PROGN (SETQ TEMP_ELE1 (APPEND (LIST (NTH 0 (NTH I PORTAL_DATA))) SM_LIST))
           (SETQ LIST2 (CONS TEMP_ELE1 LIST2))
    )
  )
  (SETQ I (+ I 1))
  )
  (APPEND (LIST LIST1) (LIST LIST2))
)




(DEFUN C:GET_BOM_GPS ( / )

 (SETQ WPT1 (GETPOINT "\nSELECT POINT1:"))
 (SETQ WPT2 (GETPOINT "\nSELECT POINT2:"))
 (SETQ WPT3 (GETPOINT "\nSELECT POINT3:"))
 (SETQ WPT4 (GETPOINT "\nSELECT POINT4:"))
 (SETQ BLOCKS_LIST (FORM_SSSET (SSGET "WP" (LIST WPT1 WPT2 WPT3 WPT4) (LIST (CONS 0 "INSERT")))))
  
 (SETQ STARTING_POINT (GETPOINT "\nSELECT STARTING POINT:"))
 (SETQ STARTING_ENTITY (LIST STARTING_POINT 1))

 
 (SETQ POLYLINE_ENTITY (CAR (ENTSEL "\nSELECT TRACK ALIGNMENT FOR UP TRACK (DN LINE):")))
  

 ;(SETQ BLOCKS_LIST (FORM_SSSET (SSGET "X" (LIST (CONS 0 "INSERT")))))
 (SETQ BLOCK_NAME_LIST (EXTRACT_ENTITY_INFO2 BLOCKS_LIST))
 (SETQ EX_CEL (GETSTRING "\n ENTER STARTING CELL NUMBER IN EXCEL SHEET:"))

(SETQ MAST_ENTITIES (YARD_DATA_COLLECT_GPS BLOCKS_LIST '("SINGLE_CANT_MAST" "DOUBLE_CANT_MAST" "TRIPLE_CANT_MAST" "TTC" "SS1" "SS2" "SS3" "SS4") 1 5))
(SETQ UPLINE_MAST_ENTITIES (FILTER_LIST '("DN") MAST_ENTITIES 1))
(SETQ DNLINE_MAST_ENTITIES (FILTER_LIST '("UP") MAST_ENTITIES 1))
(SETQ UPLINE_MAST_ENTITIES (EXTRACT_ENTITY_INFO (SINGLE_ELE_LIST UPLINE_MAST_ENTITIES 0) 1 3))
(SETQ DNLINE_MAST_ENTITIES (EXTRACT_ENTITY_INFO (SINGLE_ELE_LIST DNLINE_MAST_ENTITIES 0) 1 3))
(SETQ PORTAL_ENTITIES (YARD_DATA_COLLECT_GPS BLOCKS_LIST '("PORTAL" "SS5") 1 3))
(SETQ TTC_ENTITIES (YARD_DATA_COLLECT_GPS BLOCKS_LIST '("TTC" "SS4") 1 3))
(SETQ BUFFER_END_ENTITIES (YARD_DATA_COLLECT_GPS BLOCKS_LIST '("SS0") 1 3))

;;***************NEWLY ADDED********************************************************************************************************************;--->START
;(SETQ MAST_ENTITIES (YARD_DATA_COLLECT WPT1 WPT2 '("SINGLE_CANT_MAST" "DOUBLE_CANT_MAST" "TRIPLE_CANT_MAST" "TTC" "SS0" "SS1" "SS2" "SS3" "SS4") 1 3))
;(SETQ PORTAL_ENTITIES (YARD_DATA_COLLECT WPT1 WPT2 '("PORTAL" "SS5") 1 3))
;(SETQ PORTAL_ENDS (PORTAL_END_POINTS (SINGLE_ELE_LIST PORTAL_ENTITIES 0)))
;(SETQ PORTAL_END_UP (SINGLE_ELE_LIST PORTAL_ENDS 0))
;(SETQ PORTAL_END_DN (SINGLE_ELE_LIST PORTAL_ENDS 1))
;(SETQ PORTAL_END_UP_DN (BUILD_LIST (ADD_LISTS PORTAL_END_UP PORTAL_END_DN) '(0 1 3)))
;(SETQ MAST_WITH_LOC_NO (BUILD_LIST (ATTRIBUTES_FROM_ENTITIES MAST_ENTITIES "MAST_NUMBER1" 0) '(2 0 1)))
;(SETQ PORTAL_WITH_LOC_NO (BUILD_LIST (ATTRIBUTES_FROM_ENTITIES PORTAL_END_UP_DN "MAST_NUMBER1" 0) '(3 0 1 2)) )
;(SETQ WITH_LOC_NO (APPEND MAST_WITH_LOC_NO PORTAL_WITH_LOC_NO))
;(SETQ WITH_LOC_NO (SORT_FUN WITH_LOC_NO 0 0))
;(SETQ TOTAL_STRUCTURE_ENTITIES (REMOVE_NTH_ELE WITH_LOC_NO 0))
;;***************NEWLY ADDED********************************************************************************************************************;--->END

(SETQ CANTI_LIST (YARD_DATA_COLLECT_GPS BLOCKS_LIST  '("SINGLE_CANT_MAST"  "SINGLE_CANT_DA" "DOUBLE_CANT_MAST"  "DOUBLE_CANT_DA" "TRIPLE_CANT_MAST"  "TRIPLE_CANT_DA" "SINGLE_CANT_UPRIGHT" "DOUBLE_CANT_UPRIGHT" "TRIPLE_CANT_UPRIGHT" "SS0" "SS1" "SS2" "SS3" "BOX_TYPE") 1 3))
(SETQ MAST_TTC (YARD_DATA_COLLECT_GPS BLOCKS_LIST  '("SINGLE_CANT_MAST" "DOUBLE_CANT_MAST" "TRIPLE_CANT_MAST" "TTC" "SS0" "SS1" "SS2" "SS3" "SS4") 1 3))
(SETQ MAST_E (YARD_DATA_COLLECT_GPS BLOCKS_LIST  '("SINGLE_CANT_MAST" "DOUBLE_CANT_MAST" "TRIPLE_CANT_MAST"  "SS0" "SS1" "SS2" "SS3") 1 3))

  (SETQ PORTAL_ENDS (PORTAL_END_POINTS_GPS (SINGLE_ELE_LIST PORTAL_ENTITIES 0)))
  (SETQ PORTAL_END_UP (SINGLE_ELE_LIST PORTAL_ENDS 0))
  (SETQ PORTAL_END_DN (SINGLE_ELE_LIST PORTAL_ENDS 1))
  (SETQ PORTAL_END_UP_DN (BUILD_LIST (ADD_LISTS PORTAL_END_UP PORTAL_END_DN) '(0 1 3)))
  (SETQ MAST_PORTAL_TTC (APPEND MAST_TTC PORTAL_END_UP PORTAL_END_DN))
  (SETQ UPLINE_DATA (SORT_ENTITIES_ALONG_CURVE1 POLYLINE_ENTITY (APPEND UPLINE_MAST_ENTITIES PORTAL_END_UP_DN BUFFER_END_ENTITIES) STARTING_ENTITY 0 0));--------FINAL LIST
  (SETQ DNLINE_DATA (SORT_ENTITIES_ALONG_CURVE1 POLYLINE_ENTITY DNLINE_MAST_ENTITIES STARTING_ENTITY 0 0));----------------------------------FINAL LIST

;JUMPER/ISOLATOR/SI/PTFE/ANCHOR/PLATFORM LISTS EXTRACTION
(SETQ JUMPER_LIST (YARD_DATA_COLLECT_GPS BLOCKS_LIST  '("JUMPER") 1 3))
(SETQ ISOLATOR_LIST (YARD_DATA_COLLECT_GPS BLOCKS_LIST  '("SPS") 1 3))
(SETQ SI/PTFE_LIST (YARD_DATA_COLLECT_GPS BLOCKS_LIST  '("SI") 1 3))
(SETQ ANCHOR_LIST (YARD_DATA_COLLECT_GPS BLOCKS_LIST  '("ANCHOR" "BTB_ANC") 1 3));
(SETQ CI_LIST (YARD_DATA_COLLECT_GPS BLOCKS_LIST  '("CUTIN_INSULATOR") 1 3))
(SETQ SM_LIST (YARD_DATA_COLLECT_GPS BLOCKS_LIST  '("SUPER_MAST") 1 3))
(SETQ PLATFORM_LIST (SINGLE_ELE_LIST (YARD_DATA_COLLECT_GPS BLOCKS_LIST  '("PLATFORM") 1 3) 0))

;MAPPING OF JUMPER/ISOLATOR/SI/PTFE/ANCHOR LISTS TO STRUCTURE LISTS
(SETQ JUMPER_STRUCTURE_MAP_DATA (DATA_TO_STRUCTURE_MAP1 JUMPER_LIST CANTI_LIST 1 1))
(SETQ CI_STRUCTURE_MAP_DATA (DATA_TO_STRUCTURE_MAP1 CI_LIST CANTI_LIST 1 1))
(SETQ ISOLATOR_STRUCTURE_MAP_DATA (DATA_TO_STRUCTURE_MAP1 ISOLATOR_LIST MAST_PORTAL_TTC 1 1))
(SETQ SI/PTFE_STRUCTURE_MAP_DATA (DATA_TO_STRUCTURE_MAP1 SI/PTFE_LIST CANTI_LIST 1 1))
(SETQ ANCHOR_STRUCTURE_MAP_DATA (DATA_TO_STRUCTURE_MAP1 ANCHOR_LIST MAST_PORTAL_TTC 1 1));
(SETQ UNDER_BOOM/SM_PORTAL/TTC_MAP_DATA (EXTRACT_UB/SM_INFO_GPS (APPEND PORTAL_ENTITIES TTC_ENTITIES)))
(SETQ SM_LIST (SM_MODIFY (NTH 1 UNDER_BOOM/SM_PORTAL/TTC_MAP_DATA) SM_LIST 0))
(SETQ SM_STRUCTURE_MAP_DATA (DATA_TO_STRUCTURE_MAP_GPS SM_LIST MAST_E 1 1))
           ;;;;;;;;
(SETQ JUMPER_STRUCTURE_MAP_DATA (BUILD_LIST  JUMPER_STRUCTURE_MAP_DATA '(1 0)))
(SETQ CI_STRUCTURE_MAP_DATA (BUILD_LIST  CI_STRUCTURE_MAP_DATA '(1 0)))
(SETQ ISOLATOR_STRUCTURE_MAP_DATA (BUILD_LIST  ISOLATOR_STRUCTURE_MAP_DATA '(1 0)))
(SETQ SI/PTFE_STRUCTURE_MAP_DATA (BUILD_LIST  SI/PTFE_STRUCTURE_MAP_DATA '(1 0)))
(SETQ ANCHOR_STRUCTURE_MAP_DATA (BUILD_LIST ANCHOR_STRUCTURE_MAP_DATA '(1 0)))

(SETQ SM_STRUCTURE_MAP_DATA (BUILD_LIST SM_STRUCTURE_MAP_DATA '(1 0)))
;;;;;;;;;;;;;;;;;;;;;;;;;;;;;;;;;;;;;;;;;;;;;;;;;;;;;;;;;;;;;;;;;;;

(IF (/= UNDER_BOOM/SM_PORTAL/TTC_MAP_DATA NIL)
(PROGN (SETQ UNDER_BOOM_PORTAL/TTC_MAP_DATA (NTH 0 UNDER_BOOM/SM_PORTAL/TTC_MAP_DATA))
(SETQ SM_PORTAL/TTC_MAP_DATA (NTH 1 UNDER_BOOM/SM_PORTAL/TTC_MAP_DATA))))

(SETQ EX_CEL (PRINT_WHOLE_DATA_GPS (APPEND UPLINE_DATA DNLINE_DATA) ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST EX_CEL))
(SETQ EX_CEL (PRINT_UB_DATA UNDER_BOOM_PORTAL/TTC_MAP_DATA EX_CEL))
(SETQ EX_CEL (PRINT_SM_DATA SM_PORTAL/TTC_MAP_DATA EX_CEL))

)


(DEFUN DATA_TO_STRUCTURE_MAP_GPS
       (LIST1 LIST2 K Q / I TEMP_ELE TEMP_ELE1 LIST3)
  (SETQ I 0)
  (SETQ TEMP_ELE NIL)
  (SETQ TEMP_ELE1 NIL)
  (SETQ LIST3 NIL)
  (WHILE (< I (LENGTH LIST1))
    (IF (/= LIST2 NIL)
    (PROGN
    (SETQ TEMP_ELE1 (MAP_NEAREST1 LIST2 (NTH K (NTH I LIST1)) Q))
    (SETQ TEMP_ELE (APPEND (LIST (NTH 0 (NTH I LIST1))) TEMP_ELE1))
    (SETQ LIST3 (CONS TEMP_ELE LIST3))
    (SETQ LIST2 (VL-REMOVE TEMP_ELE1 LIST2))
    )
    )
    (SETQ I (+ I 1))
  )
  LIST3
)





;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;

                          ;SPECIAL TASK SPECIFIC FUNCTION TO SORT UPRIGHTS AND DROP ARMS AND TO MAP UPRIGHT CANTILEVERS TO THE CORRESPONDING UPRIGHT OF THE PORTAL/TTC

;INPUT LIST PATTERN ---> '(PORTAL_ENTITY , HATCH_CENTRE_POINT_OF_UPSIDE_HATCH_OF_PORTAL HATCH_CENTRE_POINT_OF_DNSIDE_HATCH_OF_PORTAL)                                              ;
;OUTPUT LIST PATTERN---> FOUR TYPES OF OUTPUT LIST PATTERNS                                                                                                                        ;
;CASE 1 :- IF DROPARM IS PRESENT AT BOTH UPSIDE UPRIGHT AND DNSIDE UPRIGHT===> '((ENTNAME_PORTAL ENTNAME_UPRIGHT1) ENTNAME_DA1 ENTNAME_DA2.......(ENTNAME_PORTAL ENTNAME_UPRIGHT1));
;CASE 2 :- IF DROPARM IS PRESENT AT THE UPSIDE UPRIGHT ONLY===> '((ENTNAME_PORTAL ENTNAME_UPRIGHT1) ENTNAME_DA1 ENTNAME_DA2.......ENTNAME_DAN))                                    ;
;CASE 3 :- IF DROPARM IS PRESENT AT THE DNSIDE UPRIGHT ONLY===> '((ENTNAME_DA1 ENTNAME_DA2.......(ENTNAME_PORTAL ENTNAME_UPRIGHT1))                                                ;
;CASE 4 :- IF NO DROPARM IS PRESENT ===> '((ENTNAME_DA1 ENTNAME_DA2.......ENTNAME_DAN))                                                                                            ;

;;;;;;;;;;;;;;REARRANGE DA'S;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;

(DEFUN SORT_DA_GPS (ENT_POINT / STRUCTURE_TYPE CANTILEVER_TYPE CANTILEVER_DA I LIST2 DISTANCE1 DISTANCE2 UP_UR DN_UR )
  (SETQ STRUCTURE_TYPE (YARD_STRUCTURE_INFO_GPS (NTH 0 ENT_POINT)))
  (SETQ CANTILEVER_TYPE (NTH 1 (ASSOC 6 STRUCTURE_TYPE)))
  (SETQ CANTILEVER_DA (FILTER_LIST '("SINGLE_CANT_DA" "DOUBLE_CANT_DA" "TRIPLE_CANT_DA" "BOX_TYPE") (EXTRACT_ENTITY_INFO CANTILEVER_TYPE 1 2) 1))
  (IF (/= CANTILEVER_DA NIL) (SETQ CANTILEVER_DA  (SINGLE_ELE_LIST (REVERSE (SORT_FUN (EXTRACT_ENTITY_INFO (SINGLE_ELE_LIST CANTILEVER_DA 0) 1 3) 1 1)) 0) ))
  (SETQ CANTILEVER_UR (FILTER_LIST '("SINGLE_CANT_UPRIGHT" "DOUBLE_CANT_UPRIGHT" "TRIPLE_CANT_UPRIGHT") (EXTRACT_ENTITY_INFO CANTILEVER_TYPE 1 2) 1))
  (IF (/= CANTILEVER_UR NIL) (SETQ CANTILEVER_UR  (REVERSE (SORT_FUN (EXTRACT_ENTITY_INFO (SINGLE_ELE_LIST CANTILEVER_UR 0) 1 3) 1 1)) ))
  (SETQ UP_UR NIL)
  (SETQ DN_UR NIL)
  (IF (/= CANTILEVER_UR NIL)
  (PROGN
  (SETQ I 0)
  (SETQ LIST2 NIL)

  (WHILE (< I (LENGTH CANTILEVER_UR))
    (IF (/= (VL-POSITION (NTH 1 (ASSOC 2 STRUCTURE_TYPE)) '("PORTAL" "SS5")) NIL)
    (PROGN (SETQ DISTANCE1 (ABS (DISTANCE2D (NTH 1 (NTH I CANTILEVER_UR)) (NTH 1 ENT_POINT))))
    (SETQ DISTANCE2 (ABS (DISTANCE2D (NTH 1 (NTH I CANTILEVER_UR)) (NTH 2 ENT_POINT))))
    (IF (< DISTANCE1 DISTANCE2) (SETQ LIST2 (CONS (LIST "UP" (NTH 0 (NTH I CANTILEVER_UR)) ) LIST2)) (SETQ LIST2 (CONS (LIST "DN" (NTH 0 (NTH I CANTILEVER_UR)) ) LIST2))))
    (PROGN (SETQ LIST2 (CONS (LIST "UP" (NTH 0 (NTH I CANTILEVER_UR)) ) LIST2))))
    (SETQ I (+ I 1))
  )
  (SETQ UP_UR (ASSOC "UP" LIST2))
  (SETQ DN_UR (ASSOC "DN" LIST2))
  )
  )
  (IF (/= UP_UR NIL) (SETQ UP_UR (LIST (LIST (NTH 0 ENT_POINT) (NTH 1 UP_UR)))))
  (IF (/= DN_UR NIL) (SETQ DN_UR (LIST (LIST (NTH 0 ENT_POINT) (NTH 1 DN_UR)))))
  (APPEND UP_UR CANTILEVER_DA DN_UR)
)

;;;;;;;;;;;;;;;;;;;;;;;;;;;;;;;;;;;;;;;;;;;;;;;;;;;;;;;;;;;;;;;;;END OF SORT DA FUNCTION;;;;;;;;;;;;;;;;;;;;;;;;;;;;;;;;;;;;;;;;;;;;;;;;;;;;;;;;;;;;;;;;;;;;;;;;;;;;;;;;;;;;;








;________________________START OF FUNCTIONS WHICH RETREIVES STAGGER DETAILS FOR MASTS,DROPARMS AND UPRIGHTS________________________________;
;___________________OUTPUTS LIST PATTERN FOR THESE FUNCTIONS ARE (("D" + STAGGER FOR IR) ("E" - STAGGER FOR IR) ("F" OOR STAGGER) ("G" LSW STAGGER) ("H" TRAMWAY))____________________________________________________;

                                                       ;   STAGGER FUNCTION -- 1  ;
                                            ; FOR MAST,UPRIGHT CANTILEVER AND DROP ARM ENTITIES ;
                                                              

;EXTRACTS STAGGER INFO
;WORKS FOR MAST,UPRIGHT CANTILEVER AND DROP ARM ENTITIES
;INPUT---->ENTITY NAME====>OUTPUT------>(("D" + STAGGER FOR IR) ("E" - STAGGER FOR IR) ("F" OOR STAGGER) ("G" LSW STAGGER) ("H" TRAMWAY));

(DEFUN GET_PULL/PUSH_OFF_GPS (ENTNAME / STRUCTURE_INFO STAGGER_INFO STRUCTURE_FLIPSTATE WIRE_NATURE I D10  E10 F10  G10 H10 TEMP_ELE LIST2)
  (SETQ STRUCTURE_INFO (YARD_STRUCTURE_INFO_GPS ENTNAME))
  (SETQ D10 0 E10 0 F10 0 G10 0 H10 0)
  (IF (/= (VL-POSITION (NTH 1 (ASSOC 2 STRUCTURE_INFO)) '("SINGLE_CANT_MAST" "DOUBLE_CANT_MAST" "TRIPLE_CANT_MAST" "SINGLE_CANT_DA" "DOUBLE_CANT_DA" "TRIPLE_CANT_DA" "SINGLE_CANT_UPRIGHT" "DOUBLE_CANT_UPRIGHT" "TRIPLE_CANT_UPRIGHT" "SS1" "SS2" "SS3" "BOX_TYPE")) NIL)
  (PROGN (SETQ ATTRIB_INFO (NTH 1 (ASSOC 4 STRUCTURE_INFO)))
  (SETQ STAGGER_INFO (SORT_FUN (FILTER_LIST '(1) (FILTER_LIST '("NULL_STAGGER" "NULL_STAGGER1" "NULL_STAGGER2" "STAGGER" "STAGGER1" "STAGGER2" "STAGGER3") ATTRIB_INFO 0) 3) 2 0))
  (SETQ STRUCTURE_FLIPSTATE (NTH 1 (ASSOC 5 STRUCTURE_INFO)))
  (SETQ WIRE_NATURE  (SINGLE_ELE_LIST  (FILTER_LIST '("WIRE_NATURE" "WIRE_NATURE1" "WIRE_NATURE2" "WIRE_NATURE3") ATTRIB_INFO 0) 1) )
  (SETQ I 0)
  (IF (/= STAGGER_INFO NIL)
  (PROGN(WHILE (< I (LENGTH STAGGER_INFO))
    (SETQ TEMP_ELE (NTH I STAGGER_INFO))
    (IF (= (VL-POSITION (NTH 0 TEMP_ELE) '("NULL_STAGGER" "NULL_STAGGER1" "NULL_STAGGER2")) NIL)
      (PROGN (IF (= (NTH 4 TEMP_ELE) STRUCTURE_FLIPSTATE)
	(PROGN (COND ((/= (VL-POSITION (NTH I WIRE_NATURE) (LIST "IR" "TIR")) NIL) (SETQ D10 (+ D10 1)))
	      ((/= (VL-POSITION (NTH I WIRE_NATURE) (LIST "OOR" "TOOR")) NIL) (SETQ F10 (+ F10 1)))
	      ((/= (VL-POSITION (NTH I WIRE_NATURE) (LIST "LSW" "TLSW")) NIL) (SETQ G10 (+ G10 1)))
	      ((= (NTH I WIRE_NATURE) "TW") (SETQ H10 (+ H10 1)))
	      ))
	(PROGN (COND ((/= (VL-POSITION (NTH I WIRE_NATURE) (LIST "IR" "TIR")) NIL) (SETQ E10 (+ E10 1)))
	      ((/= (VL-POSITION (NTH I WIRE_NATURE) (LIST "OOR" "TOOR")) NIL) (SETQ F10 (+ F10 1)))
	      ((/= (VL-POSITION (NTH I WIRE_NATURE) (LIST "LSW" "TLSW")) NIL) (SETQ G10 (+ G10 1)))
	      ((= (NTH I WIRE_NATURE) "TW") (SETQ H10 (+ H10 1)))
	      ))))
     (PROGN (COND ((/= (VL-POSITION (NTH I WIRE_NATURE) (LIST "IR" "TIR")) NIL) (SETQ D10 (+ D10 1)))
	      ((/= (VL-POSITION (NTH I WIRE_NATURE) (LIST "OOR" "TOOR")) NIL) (SETQ F10 (+ F10 1)))
	      ((/= (VL-POSITION (NTH I WIRE_NATURE) (LIST "LSW" "TLSW")) NIL) (SETQ G10 (+ G10 1)))
	      ((= (NTH I WIRE_NATURE) "TW") (SETQ H10 (+ H10 1)))
	      )))
      
      (SETQ I (+ I 1))
)))))
  (ADD_LISTS2 (LIST "D" "E" "F" "G" "H") (MAP_ELEMENTS1 (LIST (ITOA D10) (ITOA E10) (ITOA F10) (ITOA G10) (ITOA H10) ) (LIST "0") (LIST "")))
)

;;***********************************************STAGGER FUNCTIONS ENDS***********************************************************************************************************************************************************;


;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;

                                                                   ;   FINAL DATA EXTRACTION FUNCTION -- 2  ;
                                                     ; FOR GETTING ASSESMENT INFORMATION FOR ALL TYPES OF PORTALS/UPRIGHTS ;

;PROGRAM TO GET PORTAL INFO
;INPUT----> ENT_POINT_PORTAL ENT_UR ANCHOR_STRUCTURE_MAP_DATA JUMPER_STRUCTURE_MAP_DATA ISOLATOR_STRUCTURE_MAP_DATA SI/PTFE_STRUCTURE_MAP_DATA PLATFORM_LIST FLAG;
;ENT_POINT_PORTAL-->LIST PATTERN===> '(PORTAL_ENTITY , HATCH_CENTRE_POINT_OF_UPSIDE_HATCH_OF_PORTAL HATCH_CENTRE_POINT_OF_DNSIDE_HATCH_OF_PORTAL)                ;
;FLAG = 1 FOR GETTING UPLINE DETAILS                                                                                                                             ;
;FLAG = 2 FOR GETTING DNLINE DETAILS                                                                                                                             ;
;ENT_UR--> ENTITY OF THE UPRIGHT ATTACHED TO THE REQUIRED PORTAL UPRIGHT                                                                                         ;
;IF NO UPRIGHT IS PRESENT, THEN ENT_UR SHOULD BE PASSES AS NIL                                                                                                   ;
;====>OUTPUT------>(("A" KM NO.) ("B" "STRUCTURE NO.) ("C" STRUCTURE_TYPE) ("D" + STAGGER FOR IR) ("E" - STAGGER FOR IR) ("F" OOR STAGGER) ("G" LSW STAGGER) ("H" TRAMWAY) ("I" ADAPTOR/BOX)("M" CHAIR_LENGTH)("N" PLATFORM_LEVEL FOR CHAIR) ("P" ANCHOR_TYPE) ("Q" ANCHOR_NATURE) ("R" DMA) ("S"  JUMPER_TYPE) ("T"  ISOLATOR_TYPE) ("U" SECTION_INSULATOR/PTFE) ("V"  SPAN_FOR_1ST_BRACKET) ("W"  SPAN_FOR_2ND_BRACKET) ("X" SPAN_FOR_3RD_BRACKET))

(DEFUN GET_PORTAL_INFO_GPS (ENT_POINT_PORTAL ENT_UR ANCHOR_STRUCTURE_MAP_DATA  JUMPER_STRUCTURE_MAP_DATA ISOLATOR_STRUCTURE_MAP_DATA SI/PTFE_STRUCTURE_MAP_DATA CI_STRUCTURE_MAP_DATA SM_STRUCTURE_MAP_DATA PLATFORM_LIST FLAG / UR_INFO ENTNAME POINT CHAINAGE J/I/SI/PTFE PORTAL_ANCHOR_INFO PORTAL_INFO ACC STAGGER_FLAGS J/I/SI/PTFE1 SPAN_LENGTHS)
  (SETQ UR_INFO NIL)
  (SETQ ENTNAME (NTH 0 ENT_POINT_PORTAL))
  (SETQ POINT (NTH FLAG ENT_POINT_PORTAL))
  (SETQ CHAINAGE (GET_CHAINAGE_INFO_PORTAL_GPS ENTNAME FLAG))
  (SETQ J/I/SI/PTFE (GET_J/I/SI/PTFE_PORTAL ENTNAME JUMPER_STRUCTURE_MAP_DATA ISOLATOR_STRUCTURE_MAP_DATA SI/PTFE_STRUCTURE_MAP_DATA FLAG))
  (SETQ PORTAL_ANCHOR_INFO (ANCHOR_FUN ANCHOR_STRUCTURE_MAP_DATA PLATFORM_LIST (LIST ENTNAME POINT)))
  (SETQ PORTAL_INFO (FILTER_LIST1 '("") (APPEND CHAINAGE J/I/SI/PTFE PORTAL_ANCHOR_INFO)  1))

  (IF (/= ENT_UR NIL)
    (PROGN 
   (SETQ STAGGER_FLAGS (GET_PULL/PUSH_OFF_GPS ENT_UR))
   (SETQ J/I/SI/PTFE (GET_J/I/SI/PTFE ENT_UR JUMPER_STRUCTURE_MAP_DATA ISOLATOR_STRUCTURE_MAP_DATA SI/PTFE_STRUCTURE_MAP_DATA CI_STRUCTURE_MAP_DATA SM_STRUCTURE_MAP_DATA))
   (SETQ SPAN_LENGTHS (SPAN_LIST1 ENT_UR))
   (SETQ ACC (LIST (GET_ACC ENT_UR)))
   (SETQ UR_INFO (FILTER_LIST1 '("") (APPEND STAGGER_FLAGS J/I/SI/PTFE SPAN_LENGTHS ACC)  1) )))
 (SORT_FUN (APPEND PORTAL_INFO UR_INFO) 0 0)
  
)

;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;

;   FINAL DATA EXTRACTION FUNCTION -- 3  ;
                                            ; FOR GETTING ASSESMENT INFORMATION FOR ALL TYPES OF DROPARMS ATTACHED TO BOTH PORTALS AND TTC'S ;

;PROGRAM TO GET DA INFO
;INPUT----> ENT_PORTAL ENTNAME JUMPER_STRUCTURE_MAP_DATA ISOLATOR_STRUCTURE_MAP_DATA SI/PTFE_STRUCTURE_MAP_DATA PLATFORM_LIST FLAG;
;ENT_PORTAL--> PORTAL/TTC ENTITIES                                                                                                ;
;FLAG = 1 FOR ATTACHING UPLINE CHAINAGES OF PORTALS TO THE DA;                                                                    ;
;FLAG = 2 FOR ATTACHING UPLINE CHAINAGES OF PORTALS TO THE DA;                                                                    ;
;NOTE: IN CASE OF FINDING DA'S DETAILS ATTACHED TO TTC'S ** FLAG = 1 **  ALWAYS                                                   ;
;ENTNAME--> ENTITY OF THE DROP ARM ATTACHED TO THE PARTICULAR PORTAL OR TTC                                                       ;
;THERE IS NO ANCHOR_STRUCTURE_MAP_DATA AS AURGUMENT IN THIS CASE , AS DROP ARMS WILL NOT HAVE ANCHORS                             ;
;====>OUTPUT------>(("A" KM NO.) ("B" "STRUCTURE NO.) ("C" STRUCTURE_TYPE) ("D" + STAGGER FOR IR) ("E" - STAGGER FOR IR) ("F" OOR STAGGER) ("G" LSW STAGGER) ("H" TRAMWAY) ("I" ADAPTOR/BOX)("M" CHAIR_LENGTH)("N" PLATFORM_LEVEL FOR CHAIR) ("P" ANCHOR_TYPE) ("Q" ANCHOR_NATURE) ("R" DMA) ("S"  JUMPER_TYPE) ("T"  ISOLATOR_TYPE) ("U" SECTION_INSULATOR/PTFE) ("V"  SPAN_FOR_1ST_BRACKET) ("W"  SPAN_FOR_2ND_BRACKET) ("X" SPAN_FOR_3RD_BRACKET))

(DEFUN GET_DA_INFO_GPS (ENT_PORTAL ENTNAME JUMPER_STRUCTURE_MAP_DATA ISOLATOR_STRUCTURE_MAP_DATA SI/PTFE_STRUCTURE_MAP_DATA CI_STRUCTURE_MAP_DATA SM_STRUCTURE_MAP_DATA FLAG / ADAPTOR_INFO STAGGER_FLAGS J/I/SI/PTFE ACC SPAN_LENGTHS )
  (SETQ CHAINAGE (GET_CHAINAGE_INFO_DA_GPS ENT_PORTAL ENTNAME FLAG))
  (SETQ STAGGER_FLAGS (GET_PULL/PUSH_OFF_GPS ENTNAME))
  (SETQ J/I/SI/PTFE (GET_J/I/SI/PTFE ENTNAME JUMPER_STRUCTURE_MAP_DATA ISOLATOR_STRUCTURE_MAP_DATA SI/PTFE_STRUCTURE_MAP_DATA CI_STRUCTURE_MAP_DATA SM_STRUCTURE_MAP_DATA))
  (SETQ ACC (LIST (GET_ACC ENTNAME)))
  (SETQ SPAN_LENGTHS (SPAN_LIST1 ENTNAME))
  (SETQ ADAPTOR_INFO (CHAIR_ADAPTOR_FUN ENTNAME NIL))
  (APPEND CHAINAGE STAGGER_FLAGS J/I/SI/PTFE SPAN_LENGTHS ADAPTOR_INFO ACC)
)

;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;









;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;



;   FINAL DATA EXTRACTION FUNCTION -- 1  ;
                                                          ; FOR GETTING ASSESMENT INFORMATION FOR ALL TYPES OF MASTS ;

;PROGRAM TO GET MAST INFO;
;INPUT---->ENT_POINT ANCHOR_STRUCTURE_MAP_DATA JUMPER_STRUCTURE_MAP_DATA ISOLATOR_STRUCTURE_MAP_DATA SI/PTFE_STRUCTURE_MAP_DATA PLATFORM_LIST;
;ENT_POINT-->LIST PATTERN===>'(MAST_ENTITY , HATCH_CENTRE_POINT_OF_MAST)                                                                     ;
;====>OUTPUT------>(("A" KM NO.) ("B" "STRUCTURE NO.) ("C" STRUCTURE_TYPE) ("D" + STAGGER FOR IR) ("E" - STAGGER FOR IR) ("F" OOR STAGGER) ("G" LSW STAGGER) ("H" TRAMWAY) ("I" ADAPTOR/BOX)("M" CHAIR_LENGTH)("N" PLATFORM_LEVEL FOR CHAIR) ("P" ANCHOR_TYPE) ("Q" ANCHOR_NATURE) ("R" DMA) ("S"  JUMPER_TYPE) ("T"  ISOLATOR_TYPE) ("U" SECTION_INSULATOR/PTFE) ("V"  SPAN_FOR_1ST_BRACKET) ("W"  SPAN_FOR_2ND_BRACKET) ("X" SPAN_FOR_3RD_BRACKET))                                 ;
(DEFUN GET_MAST_INFO_GPS (ENT_POINT ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST / CHAINAGE STAGGER_FLAGS J/I/SI/PTFE SPAN_LENGTHS ENTNAME POINT INFO1 INFO2 INFO3 TOTAL_INFO )
  (SETQ ENTNAME (NTH 0 ENT_POINT))
  (SETQ POINT (NTH 1 ENT_POINT))
  (SETQ CHAINAGE (GET_CHAINAGE_INFO ENTNAME))
  (SETQ STAGGER_FLAGS (GET_PULL/PUSH_OFF_GPS ENTNAME))
  (SETQ J/I/SI/PTFE (GET_J/I/SI/PTFE ENTNAME JUMPER_STRUCTURE_MAP_DATA ISOLATOR_STRUCTURE_MAP_DATA SI/PTFE_STRUCTURE_MAP_DATA CI_STRUCTURE_MAP_DATA SM_STRUCTURE_MAP_DATA))
  (SETQ SPAN_LENGTHS (SPAN_LIST1 ENTNAME))
  (SETQ ACC (LIST (GET_ACC ENTNAME)))
  
  (SETQ INFO1 (APPEND CHAINAGE STAGGER_FLAGS J/I/SI/PTFE SPAN_LENGTHS ACC SM))
  (SETQ INFO2 (ANCHOR_FUN ANCHOR_STRUCTURE_MAP_DATA PLATFORM_LIST ENT_POINT))
  (SETQ INFO3 (CHAIR_ADAPTOR_FUN ENTNAME PLATFORM_LIST))
  (SETQ TOTAL_INFO (SORT_FUN (FILTER_LIST1 '("") (APPEND INFO1 INFO2 INFO3) 1) 0 0))
  TOTAL_INFO
)

;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;



;   FINAL DATA EXTRACTION FUNCTION -- 4  ;
                                                            ; FOR GETTING ASSESMENT INFORMATION FOR TTC UPRIGHTS ;

;PROGRAM TO GET TTC INFO
;INPUT----> ENT_POINT_TTC ENT_UR ANCHOR_STRUCTURE_MAP_DATA JUMPER_STRUCTURE_MAP_DATA ISOLATOR_STRUCTURE_MAP_DATA SI/PTFE_STRUCTURE_MAP_DATA PLATFORM_LIST        ;
;ENT_POINT_TTC-->LIST PATTERN===> '(TTC_ENTITY , HATCH_CENTRE_POINT_OF_TTC)                                                                                      ;
;ENT_UR--> ENTITY OF THE UPRIGHT ATTACHED TO THE REQUIRED TTC UPRIGHT                                                                                            ;
;IF NO UPRIGHT IS PRESENT, THEN ENT_UR SHOULD BE PASSES AS NIL                                                                                                   ;
;====>OUTPUT------>(("A" KM NO.) ("B" "STRUCTURE NO.) ("C" STRUCTURE_TYPE) ("D" + STAGGER FOR IR) ("E" - STAGGER FOR IR) ("F" OOR STAGGER) ("G" LSW STAGGER) ("H" TRAMWAY) ("I" ADAPTOR/BOX)("M" CHAIR_LENGTH)("N" PLATFORM_LEVEL FOR CHAIR) ("P" ANCHOR_TYPE) ("Q" ANCHOR_NATURE) ("R" DMA) ("S"  JUMPER_TYPE) ("T"  ISOLATOR_TYPE) ("U" SECTION_INSULATOR/PTFE) ("V"  SPAN_FOR_1ST_BRACKET) ("W"  SPAN_FOR_2ND_BRACKET) ("X" SPAN_FOR_3RD_BRACKET))

(DEFUN GET_TTC_INFO_GPS (ENT_POINT_TTC ENT_UR ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST / UR_INFO ENTNAME POINT CHAINAGE J/I/SI/PTFE TTC_ANCHOR_INFO TTC_INFO PORTAL_ANCHOR_INFO PORTAL_INFO STAGGER_FLAGS J/I/SI/PTFE1 SPAN_LENGTHS)
  (SETQ UR_INFO NIL)
  (SETQ ENTNAME (NTH 0 ENT_POINT_TTC))
  (SETQ POINT (NTH 1 ENT_POINT_TTC))
  (SETQ CHAINAGE (GET_CHAINAGE_INFO ENTNAME))
  (SETQ J/I/SI/PTFE (GET_J/I/SI/PTFE ENTNAME JUMPER_STRUCTURE_MAP_DATA ISOLATOR_STRUCTURE_MAP_DATA SI/PTFE_STRUCTURE_MAP_DATA CI_STRUCTURE_MAP_DATA SM_STRUCTURE_MAP_DATA))
  (SETQ TTC_ANCHOR_INFO (ANCHOR_FUN ANCHOR_STRUCTURE_MAP_DATA PLATFORM_LIST (LIST ENTNAME POINT)))
  (SETQ TTC_INFO (FILTER_LIST1 '("") (APPEND CHAINAGE J/I/SI/PTFE TTC_ANCHOR_INFO)  1))

  (IF (/= ENT_UR NIL)
    (PROGN 
   (SETQ STAGGER_FLAGS (GET_PULL/PUSH_OFF_GPS ENT_UR))
   (SETQ J/I/SI/PTFE (GET_J/I/SI/PTFE ENT_UR JUMPER_STRUCTURE_MAP_DATA ISOLATOR_STRUCTURE_MAP_DATA SI/PTFE_STRUCTURE_MAP_DATA CI_STRUCTURE_MAP_DATA SM_STRUCTURE_MAP_DATA))
   (SETQ SPAN_LENGTHS (SPAN_LIST1 ENT_UR))
   (SETQ UR_INFO (FILTER_LIST1 '("") (APPEND STAGGER_FLAGS J/I/SI/PTFE SPAN_LENGTHS)  1) )))
 (SORT_FUN (APPEND TTC_INFO UR_INFO) 0 0)
  
)

;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;




;;;;;PRINTING FUNCTION STARTS

(DEFUN PRINT_MAST_DATA_GPS (ENT_POINT ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST ACELL / MAST_DATA )

  (SETQ MAST_DATA (GET_MAST_INFO_GPS ENT_POINT ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST))
  (SETQ ACELL (PRINT_INFO_ASSESS MAST_DATA ACELL))
  ACELL
  
)


(DEFUN PRINT_PORTAL_DATA_GPS (ENT_POINT ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST ACELL / I ENTNAME POINT_UP POINT_DN SORTED_UR/DA UPRIGHT_UP UPRIGHT_DN X Y Z)
    (SETQ I 0)
    (SETQ ENTNAME  (NTH 0 ENT_POINT))
    (SETQ POINT_UP (NTH 1 ENT_POINT))
    (SETQ POINT_DN (NTH 2 ENT_POINT))
    (SETQ SORTED_UR/DA (SORT_DA_GPS ENT_POINT))
    (IF (/= SORTED_UR/DA NIL)
    (PROGN
     (IF (NOT (ATOM (NTH 0 SORTED_UR/DA))) (PROGN (SETQ UPRIGHT_UP (NTH 0 SORTED_UR/DA)) (SETQ SORTED_UR/DA (VL-REMOVE (NTH 0 SORTED_UR/DA) SORTED_UR/DA))) (PROGN (SETQ UPRIGHT_UP (LIST ENTNAME))))
    (IF (NOT (ATOM (LAST SORTED_UR/DA))) (PROGN (SETQ UPRIGHT_DN (LAST SORTED_UR/DA)) (SETQ SORTED_UR/DA (VL-REMOVE (LAST SORTED_UR/DA) SORTED_UR/DA)))(PROGN (SETQ UPRIGHT_DN (LIST ENTNAME)))))
    (PROGN (SETQ UPRIGHT_UP (LIST ENTNAME)) (SETQ UPRIGHT_DN (LIST ENTNAME))))
    
    (SETQ ACELL (PRINT_INFO_ASSESS (GET_PORTAL_INFO_GPS (LIST (NTH 0 UPRIGHT_UP) POINT_UP POINT_DN) (NTH 1 UPRIGHT_UP) ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST 1) ACELL))

    (WHILE (< I (LENGTH SORTED_UR/DA))
      (SETQ X (NTH 1 (ASSOC "B"  (GET_CHAINAGE_INFO_DA_GPS ENTNAME (NTH I SORTED_UR/DA) 1))))
      (SETQ Y (NTH 1 (ASSOC "B"  (GET_CHAINAGE_INFO_DA_GPS ENTNAME (NTH I SORTED_UR/DA) 2))))
      (IF (> X Y) (SETQ Z 1) (SETQ Z 2))
      (SETQ ACELL (PRINT_INFO_ASSESS (GET_DA_INFO_GPS ENTNAME (NTH I SORTED_UR/DA) JUMPER_STRUCTURE_MAP_DATA ISOLATOR_STRUCTURE_MAP_DATA SI/PTFE_STRUCTURE_MAP_DATA CI_STRUCTURE_MAP_DATA SM_STRUCTURE_MAP_DATA Z) ACELL))
      
      
      (SETQ I (+ I 1))
    )
  (SETQ ACELL (PRINT_INFO_ASSESS (GET_PORTAL_INFO_GPS (LIST (NTH 0 UPRIGHT_DN) POINT_UP POINT_DN) (NTH 1 UPRIGHT_DN) ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST 2) ACELL))
  ACELL
)





(DEFUN PRINT_TTC_DATA_GPS (ENT_POINT ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST ACELL / I ENTNAME POINT_UP POINT_DN SORTED_UR/DA UPRIGHT_UP UPRIGHT_DN )
    (SETQ I 0)
    (SETQ ENTNAME  (NTH 0 ENT_POINT))
    (SETQ POINT_UP (NTH 1 ENT_POINT))
    
    (SETQ SORTED_UR/DA (SORT_DA_GPS ENT_POINT))
    (IF (/= SORTED_UR/DA NIL)
    (PROGN (IF (NOT (ATOM (NTH 0 SORTED_UR/DA))) (PROGN (SETQ UPRIGHT_UP (NTH 0 SORTED_UR/DA)) (SETQ SORTED_UR/DA (VL-REMOVE (NTH 0 SORTED_UR/DA) SORTED_UR/DA))) (PROGN (SETQ UPRIGHT_UP (LIST ENTNAME)))))
    (PROGN (SETQ UPRIGHT_UP (LIST ENTNAME)))
    )
    (SETQ ACELL (PRINT_INFO_ASSESS (GET_TTC_INFO_GPS (LIST (NTH 0 UPRIGHT_UP) POINT_UP) (NTH 1 UPRIGHT_UP) ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST) ACELL))
    (SETQ I 0)
    (WHILE (< I (LENGTH SORTED_UR/DA))
      (SETQ ACELL (PRINT_INFO_ASSESS (GET_DA_INFO_GPS ENTNAME (NTH I SORTED_UR/DA) JUMPER_STRUCTURE_MAP_DATA ISOLATOR_STRUCTURE_MAP_DATA SI/PTFE_STRUCTURE_MAP_DATA CI_STRUCTURE_MAP_DATA SM_STRUCTURE_MAP_DATA 1) ACELL))
      (SETQ I (+ I 1))
    )
  
  ACELL
)


(DEFUN PRINT_WHOLE_DATA_GPS ( LIST1 ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST ACELL / I TEMP_ELE )
  
    ;"MRRC_P-I__ASSESS-III.XLSX"
    (SETQ I 0)
    (SETQ TEMP_ELE NIL)
      (WHILE (< I (LENGTH LIST1))
	(SETQ TEMP_ELE (NTH 1 (ASSOC 2 (YARD_STRUCTURE_INFO (NTH 0 (NTH I LIST1))))))
	(IF (/= (VL-POSITION TEMP_ELE '("SINGLE_CANT_MAST" "DOUBLE_CANT_MAST" "TRIPLE_CANT_MAST" "SS0" "SS1" "SS2" "SS3")) NIL)
	  (SETQ ACELL (PRINT_MAST_DATA_GPS (NTH I LIST1) ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST ACELL))
	)
	(IF (/= (VL-POSITION TEMP_ELE '("PORTAL" "SS5")) NIL)
	  (SETQ ACELL (PRINT_PORTAL_DATA_GPS (NTH I LIST1) ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST ACELL))
	)
	(IF (/= (VL-POSITION TEMP_ELE '("TTC" "SS4")) NIL)
	  (SETQ ACELL (PRINT_TTC_DATA_GPS (NTH I LIST1) ANCHOR_STRUCTURE_MAP_DATA JUMPER_STRUCTURE_MAP_DATA ISOLATOR_STRUCTURE_MAP_DATA SI/PTFE_STRUCTURE_MAP_DATA CI_STRUCTURE_MAP_DATA SM_STRUCTURE_MAP_DATA PLATFORM_LIST ACELL))
	)
      (SETQ I (+ I 1))
      )
  ACELL
     
     
)


;;;;;PRINTING FUNCTION ENDS




;   CHAINAGE FUNCTION -- 3  ;
                                                  ; ALL DROPARMS FOR PORTALS AND TTC'S ;
;TO FIND LOCATION DETAILS FOR DA'S
;INPUT---  >PORTAL/TTC_ENTITY_NAME, DROPARM_ENTITY_NAME AND FLAG  ==>  OUTPUT -----> (("A" KM NO.) ("B" DROPARM_NO.) ("C" DROPARM_TYPE))
;FLAG 1 ---> FOR ATTACHING UP LINE DETAILS OF PORTAL TO THE DROP ARM
;FLAG 2 ---> FOR ATTACHING DN LINE DETAILS OF PORTAL TO THE DROP ARM

(DEFUN GET_CHAINAGE_INFO_DA_GPS (ENT_PORTAL ENT_DA FLAG / PORTAL_CHAINAGE_INFO DA_TYPE TEMP_ELE)
 (IF (/= (VL-POSITION (NTH 1 (ASSOC 2 (YARD_STRUCTURE_INFO_GPS ENT_PORTAL))) '("PORTAL" "SS5")) NIL)
  (PROGN
  (SETQ PORTAL_CHAINAGE_INFO (GET_CHAINAGE_INFO_PORTAL_GPS ENT_PORTAL FLAG))
  (SETQ DA_TYPE (NTH 1 (ASSOC 2 (YARD_STRUCTURE_INFO_GPS ENT_DA))))
  (IF (/= (VL-POSITION DA_TYPE '("SINGLE_CANT_DA" "BOX_TYPE")) NIL)
  (SETQ TEMP_ELE (LIST "C" (STRCAT "6X6 DA" " " (NTH 1 (ASSOC "C" PORTAL_CHAINAGE_INFO))))))
  (IF (/= (VL-POSITION DA_TYPE '("DOUBLE_CANT_DA"  "TRIPLE_CANT_DA" )) NIL)
  (SETQ TEMP_ELE (LIST "C" (STRCAT "8X6 DA" " " (NTH 1 (ASSOC "C" PORTAL_CHAINAGE_INFO))))))
  
  )
   (PROGN
     (SETQ PORTAL_CHAINAGE_INFO (GET_CHAINAGE_INFO ENT_PORTAL ))
     (SETQ DA_TYPE (NTH 1 (ASSOC 2 (YARD_STRUCTURE_INFO_GPS ENT_DA))))
     (IF (/= (VL-POSITION DA_TYPE '("SINGLE_CANT_DA" "BOX_TYPE")) NIL)
     (SETQ TEMP_ELE (LIST "C" (STRCAT "6X6 DA" " " "TTU"))))
     (IF (/= (VL-POSITION DA_TYPE '("DOUBLE_CANT_DA"  "TRIPLE_CANT_DA" )) NIL)
     (SETQ TEMP_ELE (LIST "C" (STRCAT "8X6 DA" " " "TTU"))))
   )
 )
  (LIST (NTH 0 PORTAL_CHAINAGE_INFO) (NTH 1 PORTAL_CHAINAGE_INFO) TEMP_ELE)
)

;;*************************************CHAINAGE/LOCATION DATAILS FUNCTIONS ENDS************************************************************************;;;;





;THIS FUNCTION IS USED FOR DA

(DEFUN GET_CHAINAGE_INFO_PORTAL (ENTNAME FLAG / STRUCTURE_INFO ATTRIB_INFO INFO MAST_TYPE1 ELE1 ELE2)
  (SETQ STRUCTURE_INFO (YARD_STRUCTURE_INFO ENTNAME))
  (IF (/= (VL-POSITION (NTH 1 (ASSOC 2 STRUCTURE_INFO)) '("PORTAL" "SS5")) NIL)
  (PROGN 
  (SETQ ATTRIB_INFO (FILTER_LIST '("MAST_NUMBER1" "MAST_TYPE1" "MAST_NUMBER2" "MAST_TYPE2" "SS_NUMBER1" "SS_TYPE1" "SS_NUMBER2" "SS_TYPE2") (REVERSE (SORT_FUN (NTH 1 (ASSOC 4 STRUCTURE_INFO)) 2 1)) 0))
  (IF (= FLAG 1)
  (PROGN (SETQ INFO (NTH 1 (NTH 0 ATTRIB_INFO)))
  (SETQ MAST_TYPE1 (STRCAT (SUBSTR (NTH 1 (NTH 1 ATTRIB_INFO)) 1 1) "U") ))
  (PROGN (SETQ INFO (NTH 1 (NTH 2 ATTRIB_INFO)))
  (SETQ MAST_TYPE1 (STRCAT (SUBSTR (NTH 1 (NTH 3 ATTRIB_INFO)) 1 1) "U") ))
  )
  
  (SETQ	ELE2 (SUBSTR INFO
		     (+ (VL-STRING-POSITION (ASCII "/") INFO) 2)
	     )
  )
  (SETQ	ELE1 (SUBSTR INFO 1 (VL-STRING-POSITION (ASCII "/") INFO))
  )))
  (ADD_LISTS2 (LIST "A" "B" "C") (MAP_ELEMENTS1 (LIST ELE1 ELE2 MAST_TYPE1) (LIST NIL) (LIST "")))
)



;THIS FUNCTION IS USED FOR PORTAL UPRIGHTS

(DEFUN GET_CHAINAGE_INFO_PORTAL_GPS (ENTNAME FLAG / STRUCTURE_INFO ATTRIB_INFO INFO MAST_TYPE1 ELE1 ELE2 TYPE_FINAL)
   (SETQ STRUCTURE_INFO (YARD_STRUCTURE_INFO_GPS ENTNAME))
   (IF (/= (VL-POSITION (NTH 1 (ASSOC 2 STRUCTURE_INFO)) '("PORTAL" "SS5")) NIL)
   (PROGN
   (SETQ LOC_DATA_UP (FILTER_LIST '("MAST_NUMBER1" "MAST_TYPE1") (REVERSE (SORT_FUN (NTH 1 (ASSOC 4 STRUCTURE_INFO)) 2 1)) 0))
   (SETQ LOC_DATA_DN (FILTER_LIST '("MAST_NUMBER2" "MAST_TYPE2") (REVERSE (SORT_FUN (NTH 1 (ASSOC 4 STRUCTURE_INFO)) 2 1)) 0))
   (SETQ MAST_TYPE1 (SUBSTR (NTH 1 (ASSOC "MAST_TYPE1" LOC_DATA_UP)) 1 (VL-STRING-POSITION (ASCII "-") (NTH 1 (ASSOC "MAST_TYPE1" LOC_DATA_UP)))))
   (IF (= FLAG 1)
   (PROGN (SETQ INFO (NTH 1 (ASSOC "MAST_NUMBER1" LOC_DATA_UP)))
   (IF (/= (VL-POSITION MAST_TYPE1 (LIST "N" "O" "R" "G")) NIL) (SETQ TYPE_FINAL (STRCAT MAST_TYPE1 "U")))
   (IF (/= (VL-POSITION MAST_TYPE1 (LIST "NBFB")) NIL) (SETQ TYPE_FINAL "NU"))
   (IF (/= (VL-POSITION MAST_TYPE1 (LIST "OG")) NIL) (SETQ TYPE_FINAL "OU"))
   (IF (/= (VL-POSITION MAST_TYPE1 (LIST "BFB")) NIL) (SETQ TYPE_FINAL "BFBU"))
   )
   (PROGN (SETQ INFO (NTH 1 (ASSOC "MAST_NUMBER2" LOC_DATA_DN)))
   (IF (/= (VL-POSITION MAST_TYPE1 (LIST "N" "O" "R" "G")) NIL) (SETQ TYPE_FINAL (STRCAT MAST_TYPE1 "U")))
   (IF (/= (VL-POSITION MAST_TYPE1 (LIST "NBFB")) NIL) (SETQ TYPE_FINAL "BFBU"))
   (IF (/= (VL-POSITION MAST_TYPE1 (LIST "OG")) NIL) (SETQ TYPE_FINAL "GU"))
   (IF (/= (VL-POSITION MAST_TYPE1 (LIST "BFB")) NIL) (SETQ TYPE_FINAL "BFBU"))
   )
   )
   (SETQ ELE2 (SUBSTR INFO
		           (+ (VL-STRING-POSITION (ASCII "/") INFO) 2)
	      )
  )
  (SETQ	ELE1 (SUBSTR INFO 1 (VL-STRING-POSITION (ASCII "/") INFO))
  )))
  (ADD_LISTS2 (LIST "A" "B" "C") (MAP_ELEMENTS1 (LIST ELE1 ELE2 TYPE_FINAL) (LIST NIL) (LIST "")))
)




(DEFUN GET_BOX_POINTS_PORTAL ( BLOCK / BLOCK BASE_POINT ROTATION RECT_POINTS SORT_Y_POINTS SORT_X_POINTS BASE_POINTS ORTHO_POINT )
(SETQ BASE_POINT (CDR (ASSOC 10 (ENTGET BLOCK))))
(SETQ ROTATION (VLAX-GET-PROPERTY (VLAX-ENAME->VLA-OBJECT BLOCK) "ROTATION"))
(SETQ RECT_POINTS (ADD_LISTS (BUILD_LIST (FILTER_LIST (LIST "OHE-RECT-LOCATION BORDER") (Block_ename1 BLOCK) 0) (LIST 3 4)) (N_ELE_LIST 0.0 8)))
(SETQ SORT_Y_POINTS (SORT_FUN RECT_POINTS 0 1))
(SETQ TOP_POINTS (SORT_FUN (LIST (NTH 0 SORT_Y_POINTS) (NTH 1 SORT_Y_POINTS)) 0 0))
(SETQ BOTTOM_POINTS (SORT_FUN (LIST (NTH 6 SORT_Y_POINTS) (NTH 7 SORT_Y_POINTS)) 0 0))
(TRANSFORM (LIST (NTH 0 TOP_POINTS) (NTH 0 BOTTOM_POINTS) (NTH 1 BOTTOM_POINTS) (NTH 1 TOP_POINTS)) BASE_POINT  ROTATION)
)



(DEFUN GET_CANTILEVERS_GPS ( PT NAME_BLK ENAMEBLK / SS_SET I LIST1 ENAME BS_POINT TEMP_ELE LIST1)
(IF (= NAME_BLK "PORTAL" "SS5")
  (SETQ SS_SET (SSGET "F" (GET_BOX_POINTS_PORTAL ENAMEBLK) '((0 . "INSERT"))))
  (SETQ SS_SET (SSGET "F" (BLOCK_REFERENCE_LENGTHS_GPS NAME_BLK ENAMEBLK) '((0 . "INSERT"))))
)
  (SETQ I 0)
  (SETQ ENAME NIL)
  (SETQ BS_POINT NIL)
  (SETQ TEMP_ELE NIL)
  (SETQ LIST1 NIL)
  (IF (/= SS_SET NIL)
(WHILE (< I (SSLENGTH SS_SET))
      (SETQ ENAME (SSNAME SS_SET I))
  (IF (/= ENAME ENAMEBLK)
      (PROGN (SETQ BS_POINT (CDR (ASSOC 10 (ENTGET ENAME))))
      (SETQ TEMP_ELE (APPEND (LIST ENAME) BS_POINT))
      
      
      (SETQ LIST1 (CONS TEMP_ELE LIST1))))
      (SETQ I (+ I 1))
    )
(SETQ LIST1 (REVERSE (SORT_FUN LIST1 0 2)))
    )(SINGLE_ELE_LIST LIST1 0)
)



(DEFUN C:PRINT_PORTAL/TTC_DETAILS_GPS ( / WPT1 WPT2 EX_CEL1 PORTAL_ENTITIES TTC_ENTITIES EX_CEL2)
(SETQ WPT1 (GETPOINT "ENTER STARTING POINT IN LOP"))
(SETQ WPT2 (GETPOINT "\n ENTER ENDING POINT IN LOP"))
(SETQ EX_CEL1 (GETSTRING "\n ENTER STARTING CELL NUMBER IN EXCEL SHEET FOR PRINTING PORTAL DETAILS:"))
(SETQ PORTAL_ENTITIES (SINGLE_ELE_LIST (YARD_DATA_COLLECT WPT1 WPT2 '("PORTAL" "SS5") 1 3) 0))
(SETQ TTC_ENTITIES (SINGLE_ELE_LIST (YARD_DATA_COLLECT WPT1 WPT2 '("TTC" "SS4") 1 3) 0))
(IF (/= PORTAL_ENTITIES NIL) (PROGN (COUNT_PORTAL_GPS PORTAL_ENTITIES EX_CEL1) (ALERT "PRINTING OF PORTAL INFORMATION IS COMPLETED. ENTER CELL NUMBER FOR PRINTING TTC INFORMATION")) (ALERT "NO PORTALS TO PRINT"))
(SETQ EX_CEL2 (GETSTRING "ENTER STARTING CELL NUMBER IN EXCEL SHEET FOR PRINTING TTC DETAILS:"))
(COUNT_TTC TTC_ENTITIES EX_CEL2)
)



(DEFUN COUNT_PORTAL_GPS (LIST1 PCELL / I TEMP_ELE TEMP_ELE1 TEMP_ELE2 KM_NO PORTAL_NO_UP PORTAL_NO_DN PORTAL_NO PORTAL_TYPE)
(SETQ I 0)
(SETQ TEMP_ELE NIL)
(SETQ KM_NO NIL)
(SETQ TEMP_ELE1 NIL)
(SETQ TEMP_ELE2 NIL)
(SETQ PORTAL_NO_UP NIL)
(SETQ PORTAL_NO_DN NIL)
(SETQ PORTAL_NO NIL)
(SETQ PORTAL_TYPE NIL)
(OPENEXCEL (FINDFILE "rewari-final.XLSX") "EXT" T)
(WHILE ( < I (LENGTH LIST1))
  
  (SETQ TEMP_ELE1 (GET_CHAINAGE_INFO_PORTAL_GPS (NTH I LIST1) 1))
  (SETQ TEMP_ELE2 (GET_CHAINAGE_INFO_PORTAL_GPS (NTH I LIST1) 2))
  (SETQ KM_NO (NTH 1 (ASSOC "A" TEMP_ELE1)))
  (SETQ PORTAL_NO (STRCAT (NTH 1 (ASSOC "B" TEMP_ELE1)) "-" (NTH 1 (ASSOC "B" TEMP_ELE2))))
  (SETQ PORTAL_TYPE (NTH 1 (ASSOC "MAST_TYPE1"(NTH 1 (ASSOC 4 (YARD_STRUCTURE_INFO (NTH I LIST1)))))))
  (PUTCELL (COLUMN+N PCELL 0) KM_NO) 
  (PUTCELL (COLUMN+N PCELL 1) PORTAL_NO)
  (PUTCELL (COLUMN+N PCELL 2) PORTAL_TYPE)
  (SETQ PCELL (ROW+N PCELL 1))
  (SETQ I (+ I 1))
)
 (VLAX-INVOKE-METHOD (VLAX-GET-PROPERTY *EXCELAPP% "ACTIVEWORKBOOK") "SAVE")

)
