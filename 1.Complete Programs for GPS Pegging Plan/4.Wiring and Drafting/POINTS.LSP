(DEFUN GET_FEEDER_POINTS ( LIST1 / I INSERTION_POINT FLIP FINAL_LIST )

  (SETQ I 0 INSERTION_POINT NIL ROTATION NIL FLIP NIL FINAL_LIST NIL )
  (WHILE (< I (LENGTH LIST1))
    
    (SETQ INSERTION_POINT (VLAX-SAFEARRAY->LIST (VLAX-VARIANT-VALUE (VLAX-GET-PROPERTY (VLAX-ENAME->VLA-OBJECT (NTH I LIST1)) 'INSERTIONPOINT))))
    (SETQ ROTATION (VLAX-GET-PROPERTY (VLAX-ENAME->VLA-OBJECT (NTH I LIST1)) 'ROTATION))
    (SETQ FLIP (NTH 1 (NTH 0 (GET_DYNAMIC_PROPERTIES (NTH I LIST1) (LIST "STF1")))))
    
    (IF (OR (= I 0) (= I (- (LENGTH LIST1) 1)))
      
      (PROGN
      (IF (= FLIP 0)
                     (SETQ TEMP_POINT (POLAR INSERTION_POINT (+ ROTATION (/ (* 1 PI) 2)) 0.8))
                     (SETQ TEMP_POINT (POLAR INSERTION_POINT (+ ROTATION (/ (* 3 PI) 2)) 0.8))
      )
      )

      (PROGN
      (IF (= FLIP 0)
                     (SETQ TEMP_POINT (POLAR INSERTION_POINT (+ ROTATION (/ (* 1 PI) 2)) 2.8))
                     (SETQ TEMP_POINT (POLAR INSERTION_POINT (+ ROTATION (/ (* 3 PI) 2)) 2.8))
                 )
      )
      
    )

    (SETQ FINAL_LIST (CONS TEMP_POINT FINAL_LIST))
    (SETQ I (+ I 1))

  )

  (REVERSE FINAL_LIST)

)


(DEFUN GET_AEW_POINTS ( LIST1 / I INSERTION_POINT FLIP FINAL_LIST )

  (SETQ I 0 INSERTION_POINT NIL ROTATION NIL FLIP NIL FINAL_LIST NIL )
  (WHILE (< I (LENGTH LIST1))
    
    (SETQ INSERTION_POINT (VLAX-SAFEARRAY->LIST (VLAX-VARIANT-VALUE (VLAX-GET-PROPERTY (VLAX-ENAME->VLA-OBJECT (NTH I LIST1)) 'INSERTIONPOINT))))
    (SETQ ROTATION (VLAX-GET-PROPERTY (VLAX-ENAME->VLA-OBJECT (NTH I LIST1)) 'ROTATION))
    (SETQ FLIP (NTH 1 (NTH 0 (GET_DYNAMIC_PROPERTIES (NTH I LIST1) (LIST "STF1")))))
    
    (IF (OR (= I 0) (= I (- (LENGTH LIST1) 1)))
      
      (PROGN
      (IF (= FLIP 0)
                     (SETQ TEMP_POINT (POLAR INSERTION_POINT (+ ROTATION (/ (* 1 PI) 2)) 0.8))
                     (SETQ TEMP_POINT (POLAR INSERTION_POINT (+ ROTATION (/ (* 3 PI) 2)) 0.8))
      )
      )

      (PROGN
      (IF (= FLIP 0)
                     (SETQ TEMP_POINT (POLAR INSERTION_POINT (+ ROTATION (/ (* 1 PI) 2)) 1.6))
                     (SETQ TEMP_POINT (POLAR INSERTION_POINT (+ ROTATION (/ (* 3 PI) 2)) 1.6))
                 )
      )
      
    )

    (SETQ FINAL_LIST (CONS TEMP_POINT FINAL_LIST))
    (SETQ I (+ I 1))

  )

  (REVERSE FINAL_LIST)

)




(DEFUN CURVE_POINTS ( / )

  (SETQ POLYLINE_ENTITY (CAR(ENTSEL)))
  (SETQ POLYLINE_ENTITY (VLAX-ENAME->VLA-OBJECT POLYLINE_ENTITY))
  (SETQ POINT (GETPOINT))

  (SETQ DISTANCE1 (VLAX-CURVE-GETDISTATPOINT POLYLINE_ENTITY POINT))

  (SETQ POINT1 (VLAX-CURVE-GETPOINTATDIST POLYLINE_ENTITY (- DISTANCE1 0.8)))

  (SETQ POINT2 (VLAX-CURVE-GETPOINTATDIST POLYLINE_ENTITY (+ DISTANCE1 0.8)))

  (SETQ DISTANCE2 (DISTANCE POINT1 POINT2))
  (SETQ DISTANCE3 (DISTANCE_ON_CURVE_GPS POLYLINE_ENTITY POINT1 POINT2))
  
  (IF (= DISTANCE2 DISTANCE3)

    (ALERT "NOT ON CURVE")
    (ALERT "ON CURVE")

  )

)
