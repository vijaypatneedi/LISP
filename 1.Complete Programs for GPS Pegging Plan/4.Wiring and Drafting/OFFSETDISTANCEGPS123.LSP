(DEFUN C:OFFSET_DISTANCE_GPS ( / OFFSET_ENTITIES1 TRACK_ENTITY LINE TR_OFFSET_Y OFFSET_ENTITIES1 I OFFSET_ENTITIES TEMP_ELE1 LIST2 )
  (PROMPT "SELECT OFFSETS")
  (SETQ OFFSET_ENTITIES1 (SSGET))
  (SETQ TRACK_ENTITY (CAR(ENTSEL "\nSELECT TRACK ALIGNMENT:")))
  (SETQ LINE (GETSTRING "\n ENTER TRACK TYPE (UP/DN)"))
  (SETQ TR_OFFSET_Y (NTH 2 (ASSOC 10 (ENTGET TRACK_ENTITY))))
  (SETQ OFFSET_ENTITIES1 (FORM_SSSET OFFSET_ENTITIES1))
  (SETQ I 0)
  (SETQ OFFSET_ENTITIES NIL)
  (WHILE (< I (LENGTH OFFSET_ENTITIES1))
    (SETQ TEMP_ELE1 (CDR (ASSOC 10 (ENTGET (NTH I OFFSET_ENTITIES1)))))
    (SETQ OFFSET_ENTITIES (CONS (LIST (NTH I OFFSET_ENTITIES1) TEMP_ELE1) OFFSET_ENTITIES))
    (SETQ I (+ I 1))
  )
  (SETQ OFFSET_ENTITIES (REVERSE OFFSET_ENTITIES))
  (SETQ OFFSET_ENTITIES (SORT_FUN OFFSET_ENTITIES 1 0))
  
  (SETQ I 0)
  (SETQ TEMP_ELE1 NIL)
  (SETQ TEMP_ELE2 NIL)
  (SETQ TEMP_ELE3 NIL)
  (SETQ TEMP_SPAN NIL)
  (SETQ LIST2 NIL)
  (WHILE (< I (LENGTH OFFSET_ENTITIES))
  
  (IF (/= (+ I 1) (LENGTH OFFSET_ENTITIES))
 
  (PROGN
    (SETQ TEMP_ELE1 (NTH 0 (ACET-GEOM-INTERSECTWITH TRACK_ENTITY (NTH 0 (NTH I OFFSET_ENTITIES)) 0.1)))
    (SETQ TEMP_ELE2 (NTH 0 (ACET-GEOM-INTERSECTWITH TRACK_ENTITY (NTH 0 (NTH (+ I 1) OFFSET_ENTITIES)) 0.1)))
    (SETQ TEMP_SPAN (RTOS (APPROXIMATE_SPAN (DISTANCE_ON_CURVE_GPS TRACK_ENTITY TEMP_ELE2 TEMP_ELE1) 0.5) 2 2))
    (SETQ TEMP_ELE3 (VLAX-CURVE-GETPOINTATDIST TRACK_ENTITY (+ (VLAX-CURVE-GETDISTATPOINT TRACK_ENTITY TEMP_ELE1) (/ (APPROXIMATE_SPAN (DISTANCE_ON_CURVE_GPS TRACK_ENTITY TEMP_ELE2 TEMP_ELE1) 0.5) 2))))
    (IF (= LINE "DN")
    (SETQ INSERTION_POINT (POLAR TEMP_ELE3 (* 1 (/ PI 2)) 6.00))
    (SETQ INSERTION_POINT (POLAR TEMP_ELE3 (* 3 (/ PI 2)) 12.00))
    )
    (ENTMAKE (LIST
	   (CONS 0 "TEXT")
	   (CONS 1 TEMP_SPAN)
	   (LIST 10 (NTH 0 INSERTION_POINT) (NTH 1 INSERTION_POINT) 0.0)
	   (CONS 40 1.0)
	   (CONS 8 "OHE-TXT-DFCC IR TC")
	   (CONS 50 (ANGLE TEMP_ELE1 TEMP_ELE2))
	 ))
  )
 )
  (SETQ I (+ I 1))
  )
)
