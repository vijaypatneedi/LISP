(DEFUN C:HIDE_ATTRIBUTES ( / BLOCKS_LIST FLAG FLAG1 ATTR_TAG MAST_TTC_DIR MAST_UP MAST_DN)
  (SETQ BLOCKS_LIST (FORM_SSSET (SSGET "X" (LIST (CONS 0 "INSERT")))))
  (SETQ FLAG (GETSTRING "N\VISIBLE OR INVISIBLE ??? VISIBLE -> 1 INVISIBLE ->0"))
  (SETQ FLAG1 (GETINT "N\UPLINE OR DNLINE OR BOTH??? DNLINE -> 0 UPLINE ->1 BOTH -> 2"))
  (SETQ ATTR_TAG (GETSTRING "ENTER ATTRIBUTE TAGNAME"))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_UP (SINGLE_ELE_LIST (FILTER_LIST '("UP") MAST_TTC_DIR 1) 0))
  (SETQ MAST_DN (SINGLE_ELE_LIST (FILTER_LIST '("DN") MAST_TTC_DIR 1) 0))
  (IF (= FLAG1 0)
    (invis_all_fun MAST_DN FLAG ATTR_TAG)
  )
  (IF (= FLAG1 1)
    (invis_all_fun MAST_UP FLAG ATTR_TAG)
  )
 (IF (= FLAG1 2)
    (invis_all_fun (APPEND MAST_DN MAST_UP) FLAG ATTR_TAG)
  )
)





(defun invis_all_fun ( LIST1 FLAG ATTR_TAG / LIST1 FLAG)
  (vl-load-com)
    (SETQ I 0)
  (while (< I (LENGTH LIST1))
      (CHANGE_VISIBILITY (NTH I LIST1) (LIST ATTR_TAG) (LIST FLAG))
      (SETQ  I (+ I 1)))
 (princ)
)
