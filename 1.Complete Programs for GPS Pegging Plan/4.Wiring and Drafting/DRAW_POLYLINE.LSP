(DEFUN DRAW_POLYLINE ( POINT_LIST / I TEMP_ENT MYSET )

(SETQ I 0 TEMP_ENT NIL)
(SETQ MYSET (SSADD))

(WHILE (< I (- (LENGTH POINT_LIST) 1))
  
(COMMAND "LINE" (NTH I POINT_LIST) (NTH (+ I 1) POINT_LIST) "")
  
(SETQ MYSET (SSADD (ENTLAST) MYSET))
 
(SETQ I (+ I 1))
  
)


(COMMAND "PEDIT" (SSNAME MYSET 0) "" "J" MYSET "" "")
(ENTLAST)

)




(DEFUN GET_SINGLE_MAST_POINT ( ENTITY / )

   (SETQ INSERTION_POINT (VLAX-SAFEARRAY->LIST (VLAX-VARIANT-VALUE (VLAX-GET-PROPERTY (VLAX-ENAME->VLA-OBJECT ENTITY) 'INSERTIONPOINT))))

   (SETQ ROTATION (VLAX-GET-PROPERTY (VLAX-ENAME->VLA-OBJECT ENTITY) 'ROTATION))

   (SETQ IMPLANTATION (NTH 1 (NTH 0 (GET_DYNAMIC_PROPERTIES ENTITY (LIST "STL1")))))
   (SETQ FLIP (NTH 1 (NTH 0 (GET_DYNAMIC_PROPERTIES ENTITY (LIST "STF1")))))

   (IF (= FLIP 0)
     (POLAR INSERTION_POINT (+ ROTATION (/ (* 3 PI) 2)) IMPLANTATION)
     (POLAR INSERTION_POINT (+ ROTATION (/ (* 1 PI) 2)) IMPLANTATION)
   )

)


(DEFUN GET_DOUBLE_MAST_POINT ( ENTITY / )

   (SETQ INSERTION_POINT (VLAX-SAFEARRAY->LIST (VLAX-VARIANT-VALUE (VLAX-GET-PROPERTY (VLAX-ENAME->VLA-OBJECT ENTITY) 'INSERTIONPOINT))))

   (SETQ ROTATION1 (VLAX-GET-PROPERTY (VLAX-ENAME->VLA-OBJECT ENTITY) 'ROTATION))
   

   (SETQ PARAMETER_LIST (GET_DYNAMIC_PROPERTIES ENTITY (LIST "STL1" "STL2" "STS1" "STF1")))

   (SETQ LENGTH1 (NTH 1 (ASSOC "STL2" PARAMETER_LIST)))

   (SETQ LENGTH2 (NTH 1 (ASSOC "STL1" PARAMETER_LIST)))

   (SETQ LENGTH3 (NTH 1 (ASSOC "STS1" PARAMETER_LIST)))
  
   (SETQ FLIP (NTH 1 (ASSOC "STF1" PARAMETER_LIST)))

   (SETQ ROTATION2 (ATAN (/ LENGTH1 (/ LENGTH3 2))))
  
   (SETQ ROTATION3 (ATAN (/ LENGTH2 (/ LENGTH3 2))))

   (IF (= FLIP 0)
    (PROGN
     (SETQ POINT1 (POLAR INSERTION_POINT (+ (/ PI 2) (/ PI 2) ROTATION1 ROTATION2) (SQRT (+ (EXPT (/ LENGTH3 2) 2) (EXPT LENGTH1 2)))))
     (SETQ POINT2 (POLAR INSERTION_POINT (+ (- (* PI 2) ROTATION3) ROTATION1) (SQRT (+ (EXPT (/ LENGTH3 2) 2) (EXPT LENGTH2 2)))))
   )

   (PROGN
     (SETQ POINT1 (POLAR INSERTION_POINT (+ PI (- ROTATION1 ROTATION2)) (SQRT (+ (EXPT (/ LENGTH3 2) 2) (EXPT LENGTH1 2)))))
     (SETQ POINT2 (POLAR INSERTION_POINT (+  ROTATION1 ROTATION3) (SQRT (+ (EXPT (/ LENGTH3 2) 2) (EXPT LENGTH2 2)))))
   )

  )
  (LIST POINT1 POINT2)
  
)



(DEFUN GET_WIRING_POINTS ( LIST1 / I FINAL_LIST )
  (SETQ I 0 FINAL_LIST NIL)
  (WHILE (< I (LENGTH LIST1))

    (SETQ BLOCK_NAME (VLAX-GET-PROPERTY (VLAX-ENAME->VLA-OBJECT (NTH I LIST1)) 'EFFECTIVENAME))
    (SETQ ROTATION (VLAX-GET-PROPERTY (VLAX-ENAME->VLA-OBJECT (NTH I LIST1)) 'ROTATION))
    (SETQ FLIP (NTH 1 (NTH 0 (GET_DYNAMIC_PROPERTIES (NTH I LIST1) (LIST "STF1")))))
    
    (IF (OR (AND (= I 0) (= BLOCK_NAME "SINGLE_CANT_MAST")) (AND (= I (- (LENGTH LIST1) 1)) (= BLOCK_NAME "SINGLE_CANT_MAST")))
                 (PROGN
		 (SETQ INSERTION_POINT (VLAX-SAFEARRAY->LIST (VLAX-VARIANT-VALUE (VLAX-GET-PROPERTY (VLAX-ENAME->VLA-OBJECT (NTH I LIST1)) 'INSERTIONPOINT))))
                 (IF (= FLIP 0)
                     (SETQ TEMP_POINT (POLAR INSERTION_POINT (+ ROTATION (/ (* 1 PI) 2)) 0.8))
                     (SETQ TEMP_POINT (POLAR INSERTION_POINT (+ ROTATION (/ (* 3 PI) 2)) 0.8))
                 )
		 )
                 
     )


     (IF (AND (AND (/= I 0) (= BLOCK_NAME "SINGLE_CANT_MAST")) (AND (/= I (- (LENGTH LIST1) 1)) (= BLOCK_NAME "SINGLE_CANT_MAST")))
                 
                 (SETQ TEMP_POINT (GET_SINGLE_MAST_POINT (NTH I LIST1)))
     )

     (IF (AND (/= (VL-POSITION I (LIST 1 2 3)) NIL) (= BLOCK_NAME "DOUBLE_CANT_MAST"))
     (SETQ TEMP_POINT (NTH 0 (GET_DOUBLE_MAST_POINT (NTH I LIST1))))
     )

     (IF (AND (= (VL-POSITION I (LIST 1 2 3)) NIL) (= BLOCK_NAME "DOUBLE_CANT_MAST"))
     (SETQ TEMP_POINT (NTH 1 (GET_DOUBLE_MAST_POINT (NTH I LIST1)))) 
     )

    (SETQ FINAL_LIST (CONS TEMP_POINT FINAL_LIST))
    (SETQ I (+ I 1))
    
  )
(REVERSE FINAL_LIST)
)





(DEFUN C:DRAW_WIRE_RUNS( / I WPT1 WPT2 WPT3 WPT4 TRACK_ENTITY_UPTRACK BLOCKS_LIST MAST_UP MAST_DN BLOCK_NAME_LIST ACC_LIST OLC_LIST TL_LIST MAST_TTC ANCHOR_ENTITIES ANCHOR_START ANCHOR_END MAIN_LIST )
  ;(SETQ WPT1 (GETPOINT "\n ENTER 1ST POINT OF POLYGON"))
  ;(SETQ WPT2 (GETPOINT "\n ENTER 2ND POINT OF POLYGON"))
  ;(SETQ WPT3 (GETPOINT "\n ENTER 3RD POINT OF POLYGON"))
  ;(SETQ WPT4 (GETPOINT "\n ENTER 4TH POINT OF POLYGON"))
  ;(SETQ BLOCKS_LIST (FORM_SSSET (SSGET "WP" (LIST WPT1 WPT2 WPT3 WPT4) (LIST (CONS 0 "INSERT")))))
  (SETQ STARTING_POINT (GETPOINT "\nENTER STARTING POINT FOR UP TRACK (DN LINE):"))
  (SETQ STARTING_POINT_DN (GETPOINT "\nENTER STARTING POINT FOR DN TRACK (UP LINE):"))
  (SETQ BLOCKS_LIST (FORM_SSSET (SSGET "X" (LIST (CONS 0 "INSERT")))))
  (SETQ TRACK_ENTITY_UPTRACK (CAR(ENTSEL "\nSELECT TRACK ALIGNMENT FOR UP TRACK (DN LINE):")))
  (SETQ TRACK_ENTITY_DNTRACK (CAR(ENTSEL "\nSELECT TRACK ALIGNMENT FOR DN TRACK (UP LINE):")))

  (SETQ BLOCK_NAME_LIST (EXTRACT_ENTITY_INFO2 BLOCKS_LIST))
  (SETQ ACC_LIST (FILTER_LIST (LIST "ACC") BLOCK_NAME_LIST 1))
  (SETQ OLC_LIST (FILTER_LIST (LIST "OLC") BLOCK_NAME_LIST 1))
  (SETQ TL_LIST (FILTER_LIST (LIST "TENSION_LENGTH") BLOCK_NAME_LIST 1))
  (SETQ ACC_LIST (BUILD_LIST (ENTITY_DFX (SINGLE_ELE_LIST ACC_LIST 0) 10 -1) (LIST 0 1)))
  (SETQ OLC_LIST (BUILD_LIST (ENTITY_DFX (SINGLE_ELE_LIST OLC_LIST 0) 10 -1) (LIST 0 1)))
  (SETQ TL_LIST  (BUILD_LIST (ENTITY_DFX (SINGLE_ELE_LIST TL_LIST 0)  10 -1) (LIST 0 1)))
  ;(COMMAND "BURST" (ENTLAST))
  (SETQ MAST_TTC (YARD_DATA_COLLECT_GPS BLOCKS_LIST '("SINGLE_CANT_MAST" "DOUBLE_CANT_MAST" "TRIPLE_CANT_MAST" "TTC" "SS0" "SS1" "SS2" "SS3" "SS4") 1 3))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  ;(SETQ ANCHOR_LIST (YARD_DATA_COLLECT WPT1 WPT2 '("ANCHOR") 1 3))
 (SETQ ANCHOR_ENTITIES (YARD_DATA_COLLECT_GPS BLOCKS_LIST '("ANCHOR") 1 5))
 (SETQ BTB_ANCHOR_ENTITIES (YARD_DATA_COLLECT_GPS BLOCKS_LIST '("BTB_ANC") 1 3))
 (SETQ ANCHOR_START (FILTER_LIST '("START") ANCHOR_ENTITIES 1))
 (SETQ ANCHOR_END (FILTER_LIST '("END") ANCHOR_ENTITIES 1))
  
 (SETQ MAST_UP (FILTER_LIST '("UP") MAST_TTC_DIR 1))
 (SETQ MAST_DN (FILTER_LIST '("DN") MAST_TTC_DIR 1))
  
 (SETQ ANCHOR_START  (BUILD_LIST (ENTITY_DFX (SINGLE_ELE_LIST ANCHOR_START 0)  10 -1) (LIST 0 1)))
 (SETQ ANCHOR_END  (BUILD_LIST (ENTITY_DFX (SINGLE_ELE_LIST ANCHOR_END 0)  10 -1) (LIST 0 1)))

  (IF (/= ANCHOR_START NIL) (SETQ ANCHOR_START_STRUCTURE_MAP_DATA (DATA_TO_STRUCTURE_MAP_SECTIONING ANCHOR_START MAST_TTC 1 1)) (SETQ ANCHOR_START NIL))
  (IF (/= ANCHOR_END NIL) (SETQ ANCHOR_END_STRUCTURE_MAP_DATA (DATA_TO_STRUCTURE_MAP_SECTIONING ANCHOR_END MAST_TTC 1 1)) (SETQ ANCHOR_END NIL))
  (IF (/= ACC_LIST NIL) (SETQ ACC_STRUCTURE_MAP_DATA (DATA_TO_STRUCTURE_MAP_SECTIONING ACC_LIST MAST_TTC 1 1)) (SETQ ACC_STRUCTURE_MAP_DATA NIL))
  (IF (/= TL_LIST NIL) (SETQ TL_STRUCTURE_MAP_DATA (DATA_TO_STRUCTURE_MAP_SECTIONING TL_LIST MAST_TTC 1 1)) (SETQ TL_STRUCTURE_MAP_DATA NIL))
 (SETQ MAIN_LIST (MAP_TENSION_LENGTHS ANCHOR_START_STRUCTURE_MAP_DATA ANCHOR_END_STRUCTURE_MAP_DATA TL_STRUCTURE_MAP_DATA))

 
 (SETQ START_END_MAST_LIST_FOR_ACC (ADD_LISTS1 (BUILD_LIST (ENTITY_DFX (SINGLE_ELE_LIST (SINGLE_ELE_LIST MAIN_LIST 0) 0)  10 -1) (LIST 0 1))  (BUILD_LIST (ENTITY_DFX (SINGLE_ELE_LIST (SINGLE_ELE_LIST MAIN_LIST 1) 0)  10 -1) (LIST 0 1))))
 (SETQ MAST_LIST_FOR_ACC_UP (BREAK_MAST_WIRE_LENGTH_GPS START_END_MAST_LIST_FOR_ACC (BUILD_LIST (ENTITY_DFX (SINGLE_ELE_LIST MAST_UP 0) 10 -1) (LIST 0 1)) TRACK_ENTITY_UPTRACK STARTING_POINT))
 (SETQ MAST_LIST_FOR_ACC_DN (BREAK_MAST_WIRE_LENGTH_GPS START_END_MAST_LIST_FOR_ACC (BUILD_LIST (ENTITY_DFX (SINGLE_ELE_LIST MAST_DN 0) 10 -1) (LIST 0 1)) TRACK_ENTITY_UPTRACK STARTING_POINT))


 (SETQ DOUBLE_CANT_MASTS (SINGLE_ELE_LIST (YARD_DATA_COLLECT_GPS BLOCKS_LIST '("DOUBLE_CANT_MAST") 1 3) 0))

 (CHANGE_STL DOUBLE_CANT_MASTS)
  

 (SETQ I 0 CONTACT_UP NIL)
 (WHILE (< I (LENGTH MAST_LIST_FOR_ACC_UP))
   (SETQ WIRING_POINTS (GET_WIRING_POINTS (SINGLE_ELE_LIST (NTH I MAST_LIST_FOR_ACC_UP) 0)))
   (SETQ CONTACT_UP (CONS (LIST (DRAW_POLYLINE WIRING_POINTS) WIRING_POINTS) CONTACT_UP))
   (SETQ I (+ I 1))
 )


 (SETQ I 0 CONTACT_DN NIL)
 (WHILE (< I (LENGTH MAST_LIST_FOR_ACC_DN))
   (SETQ WIRING_POINTS (GET_WIRING_POINTS (SINGLE_ELE_LIST (NTH I MAST_LIST_FOR_ACC_DN) 0)))
   (SETQ CONTACT_DN (CONS (LIST (DRAW_POLYLINE WIRING_POINTS) WIRING_POINTS) CONTACT_DN))
   (SETQ I (+ I 1))
   
 )


  (SETQ ACC_POINTS_UP (GET_ACC_MASTS MAST_LIST_FOR_ACC_UP ACC_STRUCTURE_MAP_DATA))
  (SETQ ACC_POINTS_DN (GET_ACC_MASTS MAST_LIST_FOR_ACC_DN ACC_STRUCTURE_MAP_DATA))

 (SETQ I 0 ANTICREEP_UP NIL)
 (WHILE (< I (LENGTH ACC_POINTS_UP))
   (SETQ ANTICREEP_UP (CONS (LIST (DRAW_POLYLINE (NTH I ACC_POINTS_UP)) (NTH I ACC_POINTS_UP)) ANTICREEP_UP))  
   (SETQ I (+ I 1))
 )

 (SETQ I 0 ANTICREEP_DN NIL)
 (WHILE (< I (LENGTH ACC_POINTS_DN))
   (SETQ ANTICREEP_DN (CONS (LIST (DRAW_POLYLINE (NTH I ACC_POINTS_DN)) (NTH I ACC_POINTS_DN)) ANTICREEP_DN))
   (SETQ I (+ I 1))
 )



 (PLACE_CUTIN_CONTACT CONTACT_UP)
 (PLACE_CUTIN_CONTACT CONTACT_DN)



  



  (SETQ MAST_LIST_DNLINE (SORT_FUN (ENTITY_DFX (SINGLE_ELE_LIST MAST_DN 0) 10 -1) 1 0))
  (SETQ MAST_LIST_UPLINE (SORT_FUN (ENTITY_DFX (SINGLE_ELE_LIST MAST_UP 0) 10 -1) 1 0))
  
  (SETQ MAST_LIST_DNLINE (COMBINE_LIST_ELEMENTS (GET_PROJECTION_FROM_POINT_LIST_FINAL TRACK_ENTITY_UPTRACK (BUILD_LIST MAST_LIST_DNLINE (LIST 0 1)) 1)))
  (SETQ MAST_LIST_UPLINE (COMBINE_LIST_ELEMENTS (GET_PROJECTION_FROM_POINT_LIST_FINAL TRACK_ENTITY_UPTRACK (BUILD_LIST MAST_LIST_UPLINE (LIST 0 1)) 1)))
  
  (SETQ MAST_LIST_DNLINE (SORT_ENTITIES_ALONG_CURVE TRACK_ENTITY_UPTRACK MAST_LIST_DNLINE (LIST 1 STARTING_POINT) 2 1))
  (SETQ MAST_LIST_UPLINE (SORT_ENTITIES_ALONG_CURVE TRACK_ENTITY_UPTRACK MAST_LIST_UPLINE (LIST 1 STARTING_POINT) 2 1))

    (SETQ MAST_UP  (ADD_LISTS (BUILD_LIST (ENTITY_DFX (SINGLE_ELE_LIST MAST_UP 0)  10 -1) (LIST 0 1)) (N_ELE_LIST "UP" (LENGTH MAST_UP))))
  (SETQ MAST_DN  (ADD_LISTS (BUILD_LIST (ENTITY_DFX (SINGLE_ELE_LIST MAST_DN 0)  10 -1) (LIST 0 1)) (N_ELE_LIST "DN" (LENGTH MAST_DN))))
  (IF (/= BTB_ANCHOR_ENTITIES NIL) (SETQ BTB_ANCHOR_STRUCTURE_MAP_DATA_TOTAL (DATA_TO_STRUCTURE_MAP_SECTIONING BTB_ANCHOR_ENTITIES (APPEND MAST_UP MAST_DN) 1 1)) (SETQ BTB_ANCHOR_ENTITIES NIL))
  (SETQ BTB_ANCHOR_STRUCTURE_MAP_DATA_TOTAL (BUILD_LIST (SORT_ENTITIES_ALONG_CURVE1 TRACK_ENTITY_UPTRACK (ADD_LISTS BTB_ANCHOR_STRUCTURE_MAP_DATA_TOTAL (SINGLE_ELE_LIST (ENTITY_DFX (SINGLE_ELE_LIST BTB_ANCHOR_STRUCTURE_MAP_DATA_TOTAL 0)  10 -1) 1)) (LIST 1 STARTING_POINT) 1 1) (LIST 0 1 3)))
  (SETQ BTB_ANCHOR_STRUCTURE_MAP_DATA_TOTAL (ADD_LISTS BTB_ANCHOR_STRUCTURE_MAP_DATA_TOTAL (SINGLE_ELE_LIST (ATTRIBUTES_FROM_ENTITIES (SINGLE_ELE_LIST BTB_ANCHOR_STRUCTURE_MAP_DATA_TOTAL 0) "ANCHOR_TYPE1" 1) 1)))

  (SETQ FEEDER_BTB_UP (SINGLE_ELE_LIST (FILTER_LIST (LIST "FA")  (FILTER_LIST (LIST "UP") BTB_ANCHOR_STRUCTURE_MAP_DATA_TOTAL 2) 3) 1))
  (SETQ FEEDER_BTB_DN (SINGLE_ELE_LIST (FILTER_LIST (LIST "FA")  (FILTER_LIST (LIST "DN") BTB_ANCHOR_STRUCTURE_MAP_DATA_TOTAL 2) 3) 1))

  (SETQ AEW_BTB_UP (SINGLE_ELE_LIST (FILTER_LIST (LIST "AEWA")  (FILTER_LIST (LIST "UP") BTB_ANCHOR_STRUCTURE_MAP_DATA_TOTAL 2) 3) 1))
  (SETQ AEW_BTB_DN (SINGLE_ELE_LIST (FILTER_LIST (LIST "AEWA")  (FILTER_LIST (LIST "DN") BTB_ANCHOR_STRUCTURE_MAP_DATA_TOTAL 2) 3) 1))

  (SETQ MAST_LIST_DNLINE (SINGLE_ELE_LIST MAST_LIST_DNLINE 0))
  (SETQ MAST_LIST_UPLINE (SINGLE_ELE_LIST MAST_LIST_UPLINE 0))

  (SETQ FEEDER_BTB_UP (BREAK_LISTS FEEDER_BTB_UP MAST_LIST_UPLINE))
  (SETQ FEEDER_BTB_DN (BREAK_LISTS FEEDER_BTB_DN MAST_LIST_DNLINE))
  (SETQ AEW_BTB_UP (BREAK_LISTS AEW_BTB_UP MAST_LIST_UPLINE))
  (SETQ AEW_BTB_DN (BREAK_LISTS AEW_BTB_DN MAST_LIST_DNLINE))

  (SETQ FEEDER_POINTS_LIST (APPEND FEEDER_BTB_UP FEEDER_BTB_DN))
  (SETQ AEW_POINTS_LIST (APPEND AEW_BTB_UP AEW_BTB_DN))

  (SETQ I 0 FEEDER_TOTAL NIL TEMP_FEEDER_POINT_LIST NIL)
 (WHILE (< I (LENGTH FEEDER_POINTS_LIST))
   (SETQ TEMP_FEEDER_POINT_LIST (GET_FEEDER_POINTS (NTH I FEEDER_POINTS_LIST)))
   (SETQ FEEDER_TOTAL (CONS (LIST (DRAW_POLYLINE TEMP_FEEDER_POINT_LIST) TEMP_FEEDER_POINT_LIST) FEEDER_TOTAL))  
   (SETQ I (+ I 1))
 )

(SETQ I 0 AEW_TOTAL NIL TEMP_AEW_POINT_LIST NIL)
 (WHILE (< I (LENGTH AEW_POINTS_LIST))
   (SETQ TEMP_AEW_POINT_LIST (GET_AEW_POINTS (NTH I AEW_POINTS_LIST)))
   (SETQ AEW_TOTAL (CONS (LIST (DRAW_POLYLINE TEMP_AEW_POINT_LIST) TEMP_AEW_POINT_LIST) AEW_TOTAL))  
   (SETQ I (+ I 1))
 )


(PLACE_CUTIN_FEEDER FEEDER_TOTAL)
(PLACE_CUTIN_AEW AEW_TOTAL)

(PLACE_CUTIN_ACC ANTICREEP_UP)
(PLACE_CUTIN_ACC ANTICREEP_DN)
  
  
)







(DEFUN BREAK_LISTS ( LIST1 LIST2 / I FINAL_LIST TEMP_POSITION1 TEMP_POSITION2 J )

  (SETQ I 0 FINAL_LIST NIL TEMP_POSITION1 NIL TEMP_POSITION2 NIL J NIL)
  
  (WHILE (< I (- (LENGTH LIST1) 1))

    (SETQ TEMP_POSITION1 (VL-POSITION (NTH I LIST1) LIST2))
    (SETQ TEMP_POSITION2 (VL-POSITION (NTH (+ I 1) LIST1) LIST2))
    (SETQ J TEMP_POSITION1 TEMP_LIST NIL)
    (WHILE (<= J TEMP_POSITION2)
      (SETQ TEMP_LIST (CONS (NTH J LIST2) TEMP_LIST))
      (SETQ J (+ J 1))
    )

    (SETQ FINAL_LIST (CONS (REVERSE TEMP_LIST) FINAL_LIST))
    (SETQ I (+ I 1))
  )
  (REVERSE FINAL_LIST)

)



(DEFUN CHANGE_STL (LIST1 / I FLIP )

  (SETQ I 0)
  (WHILE (< I (LENGTH LIST1))
    (SETQ FLIP (NTH 1 (NTH 0 (GET_DYNAMIC_PROPERTIES (NTH I LIST1) (LIST "STF1")))))
    (IF (= FLIP 0)
    (INSERT_DYNAMIC_PROPERTIES (NTH I LIST1) (LIST "STL2" "STL1") (LIST 2.65 3.35))
    (INSERT_DYNAMIC_PROPERTIES (NTH I LIST1) (LIST "STL2" "STL1") (LIST 3.35 2.65))
    )
    (SETQ I (+ I 1))

  )

)


(DEFUN GET_ACC_MASTS ( MAST_LIST ACC_STRUCTURE_MAP_DATA / I TEMP_ACC_MAST_DATA TEMP_POSITION TEMP_LEFT_COUNT TEMP_RIGHT_COUNT TEMP_LEFT_LENGTH TEMP_RIGHT_LENGTH)
  (SETQ I 0 TEMP_ACC_MAST_DATA NIL TEMP_POSITION NIL TEMP_LEFT_COUNT NIL TEMP_RIGHT_COUNT NIL TEMP_LEFT_LENGTH NIL TEMP_RIGHT_LENGTH NIL TEMP_LEFT_MAST_DATA NIL TEMP_RIGHT_MAST_DATA NIL FINAL_LIST NIL)
  (WHILE (< I (LENGTH MAST_LIST))
    (IF (/= (FILTER_LIST (SINGLE_ELE_LIST (NTH I MAST_LIST)  0) ACC_STRUCTURE_MAP_DATA 1) NIL)
    (PROGN
    (SETQ TEMP_ACC_MAST_DATA (NTH 0 (FILTER_LIST (SINGLE_ELE_LIST (NTH I MAST_LIST)  0) ACC_STRUCTURE_MAP_DATA 1)))
    (SETQ TEMP_POSITION (VL-POSITION (NTH 1 TEMP_ACC_MAST_DATA) (SINGLE_ELE_LIST (NTH I MAST_LIST)  0)))
    (SETQ TEMP_CENTER_MAST (NTH TEMP_POSITION (SINGLE_ELE_LIST (NTH I MAST_LIST)  0)))
    (SETQ TEMP_LEFT_MAST (NTH (- TEMP_POSITION 1) (SINGLE_ELE_LIST (NTH I MAST_LIST)  0)))
    (SETQ TEMP_RIGHT_MAST (NTH (+ TEMP_POSITION 1) (SINGLE_ELE_LIST (NTH I MAST_LIST)  0)))
    (SETQ FINAL_LIST (CONS (GET_ACC_POINTS (LIST TEMP_LEFT_MAST TEMP_CENTER_MAST TEMP_RIGHT_MAST)) FINAL_LIST))
    )
    )
    (SETQ I (+ I 1))
  )
  (REVERSE FINAL_LIST)
)



(DEFUN GET_ACC_POINTS (LIST1 / I FINAL_LIST )

  (SETQ I 0 FINAL_LIST NIL)
  (WHILE (< I (LENGTH LIST1))

   (SETQ INSERTION_POINT (VLAX-SAFEARRAY->LIST (VLAX-VARIANT-VALUE (VLAX-GET-PROPERTY (VLAX-ENAME->VLA-OBJECT (NTH I LIST1)) 'INSERTIONPOINT))))
   (SETQ ROTATION (VLAX-GET-PROPERTY (VLAX-ENAME->VLA-OBJECT (NTH I LIST1)) 'ROTATION))
   (SETQ IMPLANTATION (NTH 1 (NTH 0 (GET_DYNAMIC_PROPERTIES (NTH I LIST1) (LIST "STL1")))))
   (SETQ FLIP (NTH 1 (NTH 0 (GET_DYNAMIC_PROPERTIES (NTH I LIST1) (LIST "STF1")))))
    
   (IF (/= I 1)
     (PROGN
       (IF (= FLIP 0)
                     (SETQ TEMP_POINT (POLAR INSERTION_POINT (+ ROTATION (/ (* 1 PI) 2)) 0.8))
                     (SETQ TEMP_POINT (POLAR INSERTION_POINT (+ ROTATION (/ (* 3 PI) 2)) 0.8))
       )
     )

     (PROGN
       (IF (= FLIP 0)
         (SETQ TEMP_POINT (POLAR INSERTION_POINT (+ ROTATION (/ (* 3 PI) 2)) IMPLANTATION))
         (SETQ TEMP_POINT (POLAR INSERTION_POINT (+ ROTATION (/ (* 1 PI) 2)) IMPLANTATION))
       )
     )
   )
   (SETQ FINAL_LIST (CONS TEMP_POINT FINAL_LIST))
   (SETQ I (+ I 1))
  )

  (REVERSE FINAL_LIST)

)





(DEFUN PLACE_CUTIN_CONTACT ( LIST1 / I )

    (SETQ I 0)
    (WHILE (< I (LENGTH LIST1))

      (SETQ POLYLINE_ENTITY (NTH 0 (NTH I LIST1)))
      (SETQ POLYLINE_VERTICES (NTH 1 (NTH I LIST1)))
      (VLAX-PUT-PROPERTY (VLAX-ENAME->VLA-OBJECT POLYLINE_ENTITY) 'LAYER "OHE-PLINE-CONTACT WIRE")

      (SETQ TEMP_INSERTION_POINT1 (VLAX-CURVE-GETPOINTATDIST POLYLINE_ENTITY 5))
      (SETQ TEMP_INSERTION_POINT2 (VLAX-CURVE-GETPOINTATDIST POLYLINE_ENTITY (- (VLAX-CURVE-GETDISTATPOINT POLYLINE_ENTITY (NTH 0 (REVERSE POLYLINE_VERTICES))) 5)))

      (COMMAND "INSERT" "CUTIN_INSULATOR" TEMP_INSERTION_POINT1 "1" (/ (* (ANGLE (NTH 0 POLYLINE_VERTICES) (NTH 1 POLYLINE_VERTICES)) 180) PI))
      (COMMAND "INSERT" "CUTIN_INSULATOR" TEMP_INSERTION_POINT2 "1" (/ (* (ANGLE (NTH 0 (REVERSE POLYLINE_VERTICES)) (NTH 1 (REVERSE POLYLINE_VERTICES))) 180) PI))

      
     (SETQ TEMP_POINT1 (VLAX-CURVE-GETPOINTATDIST POLYLINE_ENTITY (+ (VLAX-CURVE-GETDISTATPOINT POLYLINE_ENTITY (NTH 1 POLYLINE_VERTICES)) 10)))
     (SETQ TEMP_POINT2 (VLAX-CURVE-GETPOINTATDIST POLYLINE_ENTITY (- (VLAX-CURVE-GETDISTATPOINT POLYLINE_ENTITY (NTH 1 (REVERSE POLYLINE_VERTICES))) 10)))
     (COMMAND "BREAK" POLYLINE_ENTITY TEMP_POINT1 TEMP_POINT1)
     
     (IF (> (DISTANCE_ON_CURVE_GPS (ENTLAST) (VLAX-CURVE-GETSTARTPOINT (ENTLAST)) (VLAX-CURVE-GETENDPOINT (ENTLAST)))
			   (DISTANCE_ON_CURVE_GPS POLYLINE_ENTITY (VLAX-CURVE-GETSTARTPOINT POLYLINE_ENTITY) (VLAX-CURVE-GETENDPOINT POLYLINE_ENTITY)))
		        (PROGN
	                (SETQ TEMP_ENT1 (ENTLAST))
	                (SETQ TEMP_ENT2 POLYLINE_ENTITY)
		        )
		        (PROGN
	                (SETQ TEMP_ENT1 POLYLINE_ENTITY )
	                (SETQ TEMP_ENT2 (ENTLAST))
		        )
     )
     
     (VLAX-PUT-PROPERTY (VLAX-ENAME->VLA-OBJECT TEMP_ENT2) 'LINETYPE "OOR")            

     (COMMAND "BREAK" TEMP_ENT1 TEMP_POINT2 TEMP_POINT2)
          (SETQ TEMP_ENT (IF (< (DISTANCE_ON_CURVE_GPS (ENTLAST) (VLAX-CURVE-GETSTARTPOINT (ENTLAST)) (VLAX-CURVE-GETENDPOINT (ENTLAST)))
			   (DISTANCE_ON_CURVE_GPS TEMP_ENT1 (VLAX-CURVE-GETSTARTPOINT TEMP_ENT1) (VLAX-CURVE-GETENDPOINT TEMP_ENT1)))
	                (ENTLAST)
	                TEMP_ENT1
		        ))
     (VLAX-PUT-PROPERTY (VLAX-ENAME->VLA-OBJECT TEMP_ENT) 'LINETYPE "OOR")

     (SETQ I (+ I 1))

    )


)



(DEFUN PLACE_CUTIN_ACC ( LIST1 / I )

    (SETQ I 0)
    (WHILE (< I (LENGTH LIST1))

      (SETQ POLYLINE_ENTITY (NTH 0 (NTH I LIST1)))
      (SETQ POLYLINE_VERTICES (NTH 1 (NTH I LIST1)))
      (VLAX-PUT-PROPERTY (VLAX-ENAME->VLA-OBJECT POLYLINE_ENTITY) 'LAYER "OHE-PLINE-CONTACT WIRE")
      (SETQ TEMP_INSERTION_POINT1 (VLAX-CURVE-GETPOINTATDIST POLYLINE_ENTITY 5))
      (SETQ TEMP_INSERTION_POINT2 (VLAX-CURVE-GETPOINTATDIST POLYLINE_ENTITY (- (VLAX-CURVE-GETDISTATPOINT POLYLINE_ENTITY (NTH 0 (REVERSE POLYLINE_VERTICES))) 5)))

      (COMMAND "INSERT" "CUTIN_INSULATOR" TEMP_INSERTION_POINT1 "1" (/ (* (ANGLE (NTH 0 POLYLINE_VERTICES) (NTH 1 POLYLINE_VERTICES)) 180) PI))
      (COMMAND "INSERT" "CUTIN_INSULATOR" TEMP_INSERTION_POINT2 "1" (/ (* (ANGLE (NTH 0 (REVERSE POLYLINE_VERTICES)) (NTH 1 (REVERSE POLYLINE_VERTICES))) 180) PI))

      


     (SETQ I (+ I 1))

    )


)




(DEFUN PLACE_CUTIN_FEEDER ( LIST1 / I )

    (SETQ I 0)
    (WHILE (< I (LENGTH LIST1))

      (SETQ POLYLINE_ENTITY (NTH 0 (NTH I LIST1)))
      (SETQ POLYLINE_VERTICES (NTH 1 (NTH I LIST1)))
      (VLAX-PUT-PROPERTY (VLAX-ENAME->VLA-OBJECT POLYLINE_ENTITY) 'LAYER "OHE-PLINE-FEEDER WIRE")
      (SETQ TEMP_INSERTION_POINT1 (VLAX-CURVE-GETPOINTATDIST POLYLINE_ENTITY 1))
      (SETQ TEMP_INSERTION_POINT2 (VLAX-CURVE-GETPOINTATDIST POLYLINE_ENTITY (- (VLAX-CURVE-GETDISTATPOINT POLYLINE_ENTITY (NTH 0 (REVERSE POLYLINE_VERTICES))) 1)))

      (COMMAND "INSERT" "CUTIN_INSULATOR" TEMP_INSERTION_POINT1 "1" (/ (* (ANGLE (NTH 0 POLYLINE_VERTICES) (NTH 1 POLYLINE_VERTICES)) 180) PI))
      (COMMAND "INSERT" "CUTIN_INSULATOR" TEMP_INSERTION_POINT2 "1" (/ (* (ANGLE (NTH 0 (REVERSE POLYLINE_VERTICES)) (NTH 1 (REVERSE POLYLINE_VERTICES))) 180) PI))

      


     (SETQ I (+ I 1))

    )


)


(DEFUN PLACE_CUTIN_AEW ( LIST1 / I )

    (SETQ I 0)
    (WHILE (< I (LENGTH LIST1))

      (SETQ POLYLINE_ENTITY (NTH 0 (NTH I LIST1)))
      (SETQ POLYLINE_VERTICES (NTH 1 (NTH I LIST1)))
      (VLAX-PUT-PROPERTY (VLAX-ENAME->VLA-OBJECT POLYLINE_ENTITY) 'LAYER "OHE-PLINE-AERIAL EARTH WIRE")
      (SETQ I (+ I 1))

    )


)
