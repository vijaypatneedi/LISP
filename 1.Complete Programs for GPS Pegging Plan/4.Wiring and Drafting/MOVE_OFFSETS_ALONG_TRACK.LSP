(DEFUN C:MOVE_OFFSETS_ALONG_TRACK ( / TRACK_ENTITY OFFSET_ENTITIES1 SNAP_POINTS POINT1 POINT2 DIST OS_MODE 3DOS_MODE DIRECTION I TEMP_ELE TEMP_DISTANCE NEXT_POINT)
  
  (COMMAND "UCS" "W")
  (SETQ TRACK_ENTITY (CAR(ENTSEL "\n SELECT TRACK REFERENCE")))
  (SETQ OFFSET_ENTITIES1 (SSGET))
  (SETQ SNAP_POINTS (GET_OFFSET_INTERSECTION_POINTS OFFSET_ENTITIES1 TRACK_ENTITY))
  (SETQ POINT1 (GETPOINT "\n PICK STARTING POINT ON CURVE"))
  (SETQ POINT2 (GETPOINT "\n PICK ANY POINT ON CURVE IN REQUIRED DIRECTION "))
  (SETQ DIST (GETREAL "\n ENTER DISTANCE TO MOVE: "))
  (SETQ STR (GETSTRING "\n ENTER DN LINE (D) OR UPLINE (U) OR : "))
  (SETQ OS_MODE (GETVAR "OSMODE"))
  (SETQ 3DOS_MODE (GETVAR "3DOSMODE"))
  (SETVAR "OSMODE" 0)
  (SETVAR "3DOSMODE" 0)
  (SETQ DIRECTION (FIND_DIRECTION TRACK_ENTITY POINT1 POINT2))
  
  (SETQ I 0 TEMP_ELE NIL TEMP_DISTANCE NIL NEXT_POINT NIL)
  (WHILE (< I (LENGTH SNAP_POINTS))
    
    (SETQ TEMP_DISTANCE (VLAX-CURVE-GETDISTATPOINT TRACK_ENTITY (NTH 1 (NTH I SNAP_POINTS))))
    
    (IF (= DIRECTION "POSITIVE")
      (SETQ TEMP_DISTANCE (- TEMP_DISTANCE DIST))
      (SETQ TEMP_DISTANCE (+ TEMP_DISTANCE DIST))
    )
    
    (SETQ NEXT_POINT (VLAX-CURVE-GETPOINTATDIST TRACK_ENTITY TEMP_DISTANCE))
    
    (MOVE_ORTHOGONAL2 TRACK_ENTITY (NTH 0 (NTH I SNAP_POINTS)) (NTH 1 (NTH I SNAP_POINTS)) NEXT_POINT STR)
    
    ;(VLAX-PUT-PROPERTY (VLAX-ENAME->VLA-OBJECT (NTH 0 (NTH I SNAP_POINTS))) 'COLOR 2)
    (SETQ I (+ I 1))
 
  )


  (SETVAR "OSMODE" OS_MODE)
  (SETVAR "3DOSMODE" 3DOS_MODE)
  (COMMAND "UCS" "P")
    
)



(DEFUN MOVE_ORTHOGONAL2 (POLYLINE_ENTITY OBJECT PREVIOUS_POINT POINT STR / ANGLE1 DERIVATIVE SLOPE OBJECT1 POINTS_LIST OBJECT_VLA)
(SETQ ANGLE1 (VLAX-CURVE-GETPARAMATPOINT POLYLINE_ENTITY POINT))
(SETQ DERIVATIVE (VLAX-CURVE-GETFIRSTDERIV POLYLINE_ENTITY ANGLE1))
(SETQ SLOPE (+ (/ PI 2) (ANGLE '(0 0 0) DERIVATIVE)))
(COMMAND "MOVE" OBJECT "" PREVIOUS_POINT POINT)
(SETQ OBJECT1 OBJECT)
(SETQ POINTS_LIST (ADD_LISTS (BUILD_LIST (FILTER_LIST (LIST 10 11) (ENTGET OBJECT1) 0) (LIST 1 2)) (N_ELE_LIST 0.0 2)))
(SETQ OBJECT_VLA (VLAX-ENAME->VLA-OBJECT OBJECT1))
;(VLAX-INVOKE-METHOD (VLAX-ENAME->VLA-OBJECT OBJECT1) "ROTATE" (VLAX-3D-POINT (VLAX-CURVE-GETPOINTATDIST POLYLINE_ENTITY DIST)) (- (VLAX-GET-PROPERTY (VLAX-ENAME->VLA-OBJECT OBJECT1) "ANGLE") SLOPE))
(IF (= (VL-POSITION (CDR(ASSOC 0 (ENTGET OBJECT1))) (LIST "XLINE" "RAY")) NIL)
  (COMMAND "ROTATE" OBJECT1 "" POINT "R" (NTH 0 POINTS_LIST) (NTH 1 POINTS_LIST) (/ (* SLOPE 180) PI))
  (IF (= STR "D")
  (COMMAND "ROTATE" OBJECT1 "" POINT "R" (VLAX-SAFEARRAY->LIST (VLAX-VARIANT-VALUE (VLAX-GET-PROPERTY OBJECT_VLA "BASEPOINT"))) (VLAX-SAFEARRAY->LIST (VLAX-VARIANT-VALUE (VLAX-GET-PROPERTY OBJECT_VLA "SECONDPOINT"))) (/ (* SLOPE 180) PI))
  (COMMAND "ROTATE" OBJECT1 "" POINT "R" (VLAX-SAFEARRAY->LIST (VLAX-VARIANT-VALUE (VLAX-GET-PROPERTY OBJECT_VLA "BASEPOINT"))) (VLAX-SAFEARRAY->LIST (VLAX-VARIANT-VALUE (VLAX-GET-PROPERTY OBJECT_VLA "SECONDPOINT"))) ( - (/ (* SLOPE 180) PI) 180))
  )
)
)
