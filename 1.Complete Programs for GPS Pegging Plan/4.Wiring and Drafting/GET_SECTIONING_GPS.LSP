(DEFUN C:GET_SECTIONING_GPS ( / WPT1 WPT2 POINT SCALE BLOCKS_LIST BLOCK_NAME_LIST KM_STONE_LIST ACC_LIST OLC_LIST KM_STONE_LIST ACC_LIST OLC_LIST MAST_TTC ANCHOR_LIST POINT_LIST ANCHOR_LIST ANCHOR_STRUCTURE_MAP_DATA ACC_STRUCTURE_MAP_DATA OLC_STRUCTURE_MAP_DATA)
  (SETQ WPT1 (GETPOINT "\n PICK POINT1"))
  (SETQ WPT2 (GETPOINT "\n PICK POINT2"))
  (SETQ WPT3 (GETPOINT "\n PICK POINT3"))
  (SETQ WPT4 (GETPOINT "\n PICK POINT4"))
  (SETQ BLOCKS_LIST (FORM_SSSET (SSGET "WP" (LIST WPT1 WPT2 WPT3 WPT4) (LIST (CONS 0 "INSERT")))))
  (SETQ TRACK_ENTITY_UPTRACK (CAR(ENTSEL "\n SELECT DN LINE TRACK" )))
  (SETQ POINT (GETPOINT "\n ENTER INSERTION POINT"))
  (SETQ SCALE (GETINT "\n ENTER SCALE"))
  (SETQ BLOCK_NAME_LIST (EXTRACT_ENTITY_INFO2 BLOCKS_LIST))
  (SETQ KM_STONE_LIST (FILTER_LIST (LIST "KM_NEW" "KM_STONE" "KMNEW" "KMSTONE") BLOCK_NAME_LIST 1))
  (SETQ ACC_LIST (FILTER_LIST (LIST "ACC") BLOCK_NAME_LIST 1)) 
  (SETQ OLC_LIST (FILTER_LIST (LIST "OLC") BLOCK_NAME_LIST 1))
  
  (SETQ KM_STONE_COORDINATES (COMBINE_LIST_ELEMENTS (GET_PROJECTION_FROM_POINT_LIST_FINAL TRACK_ENTITY_UPTRACK (BUILD_LIST (ENTITY_DFX (SINGLE_ELE_LIST KM_STONE_LIST 0) 10 -1) (LIST 0 1)) 1)))
  (SETQ KM_STONE_LIST (REVERSE (SINGLE_ELE_LIST (SORT_ENTITIES_ALONG_CURVE TRACK_ENTITY_UPTRACK KM_STONE_COORDINATES (ASSOC (NTH 0 (NTH 0 KM_STONE_COORDINATES)) KM_STONE_COORDINATES) 2 2) 0)))
  
  (SETQ ACC_LIST (BUILD_LIST (ENTITY_DFX (SINGLE_ELE_LIST ACC_LIST 0) 10 -1) (LIST 0 1)))
  (SETQ OLC_LIST (BUILD_LIST (ENTITY_DFX (SINGLE_ELE_LIST OLC_LIST 0) 10 -1) (LIST 0 1)))
  (COMMAND "INSERT" "SECTIONING_FORMAT" POINT "1" "0" )
  (INSERT_DYNAMIC_PROPERTIES (ENTLAST) (LIST "FORMAT_LENGTH" "UP_LEFT_FLIP" "DN_RIGHT_FLIP")  (LIST (+ (* (- (LENGTH KM_STONE_LIST) 1) (/ 1000 SCALE)) 185.9044) 1 1))
  ;(COMMAND "BURST" (ENTLAST))
  (SETQ MAST_TTC (YARD_DATA_COLLECT_GPS BLOCKS_LIST '("SINGLE_CANT_MAST" "DOUBLE_CANT_MAST" "TRIPLE_CANT_MAST" "TTC" "SS0" "SS1" "SS2" "SS3" "SS4") 1 3))
  (SETQ ANCHOR_LIST (YARD_DATA_COLLECT_GPS BLOCKS_LIST '("ANCHOR" "BTB_ANC")  1 3))
  (IF (/= ANCHOR_LIST NIL) (SETQ ANCHOR_STRUCTURE_MAP_DATA (DATA_TO_STRUCTURE_MAP_SECTIONING ANCHOR_LIST MAST_TTC 1 1)) (SETQ ANCHOR_STRUCTURE_MAP_DATA NIL))
  (IF (/= ACC_LIST NIL) (SETQ ACC_STRUCTURE_MAP_DATA (DATA_TO_STRUCTURE_MAP_SECTIONING ACC_LIST MAST_TTC 1 1)) (SETQ ACC_STRUCTURE_MAP_DATA NIL))
  (IF (/= OLC_LIST NIL) (SETQ OLC_STRUCTURE_MAP_DATA (DATA_TO_STRUCTURE_MAP_SECTIONING OLC_LIST MAST_TTC 1 1)) (SETQ OLC_STRUCTURE_MAP_DATA NIL))
  (SETQ POINT (LIST (+ (CAR POINT) 92.9522) (+ (CADR POINT) 124.9774) 0.0))
  (SETQ POINT_LIST (KM_NOTATION_SECTIONING KM_STONE_LIST POINT SCALE))
  (IF (/= ANCHOR_LIST NIL) (ANCHOR_NOTATION_SECTIONING_GPS (INCLUDE_KM_NUMBER ANCHOR_STRUCTURE_MAP_DATA) POINT_LIST POINT SCALE))
  (IF (/= ACC_LIST NIL) (ACC_NOTATION_SECTIONING_GPS (INCLUDE_KM_NUMBER ACC_STRUCTURE_MAP_DATA) POINT_LIST SCALE))
  (IF (/= OLC_LIST NIL) (OLC_NOTATION_SECTIONING_GPS (INCLUDE_KM_NUMBER OLC_STRUCTURE_MAP_DATA) POINT_LIST POINT SCALE))
)





(DEFUN ANCHOR_NOTATION_SECTIONING_GPS (ANCHOR_STRUCTURE POINT_LIST POINT1 SCALE / I INS_PT INS_PT1 POINT ANCHOR EFF_NAME MAST MAST_CHAINAGE_DETAILS MAST_FLIP MAST_FLAG)
  (SETQ I 0)
  (SETQ INS_PT NIL POINT NIL ANCHOR NIL MAST NIL MAST_CHAINAGE_DETAILS NIL MAST_FLIP NIL)
  (WHILE (< I (LENGTH ANCHOR_STRUCTURE))
  (SETQ ANCHOR (NTH 0 (NTH I ANCHOR_STRUCTURE)) MAST (NTH 1 (NTH I ANCHOR_STRUCTURE)))
  (SETQ EFF_NAME (VLAX-GET-PROPERTY (VLAX-ENAME->VLA-OBJECT MAST) "EFFECTIVENAME"))
  (SETQ ANCHOR_ATTRIBUTES (NTH 1 (NTH 0 (FILTER_LIST (LIST "ANCHOR_TYPE1") (GET_ATTRIBUTES ANCHOR) 0))))
  (SETQ MAST_ATTRIBUTES (NTH 1 (NTH 0 (FILTER_LIST (LIST "CHAINAGE1") (GET_ATTRIBUTES MAST) 0))))
  (SETQ MAST_FLIP (NTH 1 (NTH 0 (GET_DYNAMIC_PROPERTIES MAST (LIST "STF1")))))
  (IF (/= (ASSOC (NTH 2 (NTH I ANCHOR_STRUCTURE)) POINT_LIST) NIL)
  (PROGN
  (SETQ POINT (NTH 1 (ASSOC (NTH 2 (NTH I ANCHOR_STRUCTURE)) POINT_LIST)))
  (IF (= EFF_NAME "SINGLE_CANT_MAST") (SETQ MAST_FLAG 0) (SETQ MAST_FLAG 1))
  (IF (= MAST_FLIP MAST_FLAG)
      (PROGN (SETQ INS_PT (LIST (+ (CAR POINT) (/ (ATOF (SUBSTR MAST_ATTRIBUTES (+ (VL-STRING-POSITION (ASCII "/") MAST_ATTRIBUTES) 2))) SCALE))  (- (CADR POINT) 26) 0.0))
	     
	     (IF (= ANCHOR_ATTRIBUTES "AEWA") (SETQ INS_PT1 (LIST (CAR INS_PT)  (+ (CADR POINT1) 22.7513) 0.0)))
	     (IF (= ANCHOR_ATTRIBUTES "FA") (SETQ INS_PT1 (LIST (CAR INS_PT)  (+ (CADR POINT1) 30.5025) 0.0)))
      )
      (PROGN
      (SETQ INS_PT (LIST (+ (CAR POINT) (/ (ATOF (SUBSTR MAST_ATTRIBUTES (+ (VL-STRING-POSITION (ASCII "/") MAST_ATTRIBUTES) 2))) SCALE))  (- (CADR POINT) 222) 0.0))
      
      (IF (= ANCHOR_ATTRIBUTES "AEWA") (SETQ INS_PT1 (LIST (CAR INS_PT)  (- (CADR POINT1) 22.7513) 0.0)))
      (IF (= ANCHOR_ATTRIBUTES "FA") (SETQ INS_PT1 (LIST (CAR INS_PT)  (- (CADR POINT1) 30.5025) 0.0)))
      )
  )
  (COMMAND "INSERT" "REPRESENTATION3" INS_PT "1" "0" )
  (MODIFY_ATTRIBUTES (ENTLAST) (LIST "TEXT1" "TEXT2") (LIST ANCHOR_ATTRIBUTES MAST_ATTRIBUTES))
  
  (IF (OR (= ANCHOR_ATTRIBUTES "FA") (= ANCHOR_ATTRIBUTES "AEWA"))
    (PROGN
    (COMMAND "INSERT" "BTB_SCH" INS_PT1 "1" "0" )
    (IF (/= MAST_FLIP MAST_FLAG) (INSERT_DYNAMIC_PROPERTIES (ENTLAST) (LIST "ACF1")  (LIST 1)))
    )
  )
  ))
  (SETQ I (+ I 1))
  )
)





(DEFUN ACC_NOTATION_SECTIONING_GPS (ACC_STRUCTURE POINT_LIST SCALE / I INS_PT INS_PT1 ACC ACC_ATTRIBUTES MAST_ATTRIBUTES MAST_FLIP ACC_FLIP POINT MAST_COUNT1_POINT MAST_COUNT2_POINT ANCHOR MAST MAST_CHAINAGE_DETAILS MAST_FLIP ACC_NATURE)
  (SETQ I 0)
  (SETQ INS_PT NIL ANCHOR NIL MAST NIL MAST_CHAINAGE_DETAILS NIL MAST_FLIP NIL)
  (WHILE (< I (LENGTH ACC_STRUCTURE))
  (SETQ ACC (NTH 0 (NTH I ACC_STRUCTURE)) MAST (NTH 1 (NTH I ACC_STRUCTURE)))
  (SETQ ACC_ATTRIBUTES (GET_ATTRIBUTES ACC))
  (SETQ MAST_ATTRIBUTES (NTH 1 (NTH 0 (FILTER_LIST (LIST "CHAINAGE1") (GET_ATTRIBUTES MAST) 0))))
  (SETQ MAST_FLIP (NTH 1 (NTH 0 (GET_DYNAMIC_PROPERTIES MAST (LIST "STF1")))))
  (SETQ ACC_FLIP (NTH 1 (NTH 0 (GET_DYNAMIC_PROPERTIES ACC (LIST "ACF1")))))
  (IF (/= (ASSOC (NTH 2 (NTH I ACC_STRUCTURE)) POINT_LIST) NIL)
  (PROGN
  (SETQ POINT (NTH 1 (ASSOC (NTH 2 (NTH I ACC_STRUCTURE)) POINT_LIST)))
  (IF (= MAST_FLIP 0)
      (PROGN
      (SETQ INS_PT1 (LIST (+ (CAR POINT) (/ (ATOF (SUBSTR MAST_ATTRIBUTES (+ (VL-STRING-POSITION (ASCII "/") MAST_ATTRIBUTES) 2))) SCALE))  (- (CADR POINT) 26) 0.0))
      (SETQ INS_PT (LIST (+ (CAR POINT) (/ (ATOF (SUBSTR MAST_ATTRIBUTES (+ (VL-STRING-POSITION (ASCII "/") MAST_ATTRIBUTES) 2))) SCALE))  (- (CADR POINT) 86.00) 0.0))
      )
      (PROGN
      (SETQ INS_PT1 (LIST (+ (CAR POINT) (/ (ATOF (SUBSTR MAST_ATTRIBUTES (+ (VL-STRING-POSITION (ASCII "/") MAST_ATTRIBUTES) 2))) SCALE))  (- (CADR POINT) 222) 0.0))
      (SETQ INS_PT (LIST (+ (CAR POINT) (/ (ATOF (SUBSTR MAST_ATTRIBUTES (+ (VL-STRING-POSITION (ASCII "/") MAST_ATTRIBUTES) 2))) SCALE))  (- (CADR POINT) 185.00) 0.0))
      )
  )
  (COMMAND "INSERT" "ACC1" INS_PT "1" "0" )
  (MODIFY_ATTRIBUTES (ENTLAST) (SINGLE_ELE_LIST ACC_ATTRIBUTES 0)  (SINGLE_ELE_LIST ACC_ATTRIBUTES 1))
  (INSERT_DYNAMIC_PROPERTIES (ENTLAST) (LIST "ACF1")  (LIST ACC_FLIP))
  (SETQ MAST_COUNT1_POINT (NTH 2 (ASSOC "MAST_COUNT1" (GET_ATTRIBUTES (ENTLAST)))) MAST_COUNT2_POINT (NTH 2 (ASSOC "MAST_COUNT2" (GET_ATTRIBUTES (ENTLAST)))) ACC_NATURE (NTH 2 (ASSOC "ACC_NATURE" (GET_ATTRIBUTES (ENTLAST)))))
  (IF (= ACC_FLIP 1) (INSERT_ATTRIBUTES (ENTLAST) (LIST "MAST_COUNT1" "MAST_COUNT2")  (LIST (LIST (CAR MAST_COUNT1_POINT) (- (CADR MAST_COUNT1_POINT) 5.5) 0.0) (LIST (CAR MAST_COUNT2_POINT) (- (CADR MAST_COUNT2_POINT) 5.5) 0.0))))
  (INSERT_ATTRIBUTES (ENTLAST) (LIST "ACC_NATURE" )  (LIST (LIST (- (CAR ACC_NATURE) 2.5) (CADR ACC_NATURE) 0.0)))
  (COMMAND "INSERT" "REPRESENTATION3" INS_PT1 "1" "0" )
  (MODIFY_ATTRIBUTES (ENTLAST) (LIST "TEXT1" "TEXT2") (LIST "ACC" MAST_ATTRIBUTES))
  )
  )
  (SETQ I (+ I 1))
  )
)


(DEFUN OLC_NOTATION_SECTIONING_GPS (ACC_STRUCTURE POINT_LIST POINT1 SCALE / I INS_PT POINT ANCHOR MAST MAST_CHAINAGE_DETAILS MAST_FLIP)
  (SETQ I 0)
  (SETQ INS_PT NIL ANCHOR NIL MAST NIL MAST_CHAINAGE_DETAILS NIL MAST_FLIP NIL)
  (WHILE (< I (LENGTH ACC_STRUCTURE))
  (SETQ ACC (NTH 0 (NTH I ACC_STRUCTURE)) MAST (NTH 1 (NTH I ACC_STRUCTURE)))
  (SETQ ACC_ATTRIBUTES (GET_ATTRIBUTES ACC))
  (SETQ MAST_ATTRIBUTES (NTH 1 (NTH 0 (FILTER_LIST (LIST "CHAINAGE1") (GET_ATTRIBUTES MAST) 0))))
  (SETQ MAST_FLIP (NTH 1 (NTH 0 (GET_DYNAMIC_PROPERTIES MAST (LIST "STF1")))))
  (IF (/= (ASSOC (NTH 2 (NTH I ACC_STRUCTURE)) POINT_LIST) NIL)
  (PROGN
  (SETQ POINT (NTH 1 (ASSOC (NTH 2 (NTH I ACC_STRUCTURE)) POINT_LIST)))
  ;(SETQ ACC_FLIP (NTH 1 (NTH 0 (GET_DYNAMIC_PROPERTIES ACC (LIST "ACF1")))))
  ;(SETQ MAST_COUNT1_POINT (NTH 2 (ASSOC "MAST_COUNT1" ACC_ATTRIBUTES))
  (IF (= MAST_FLIP 0)
      (PROGN
      (SETQ INS_PT (LIST (+ (CAR POINT) (/ (ATOF (SUBSTR MAST_ATTRIBUTES (+ (VL-STRING-POSITION (ASCII "/") MAST_ATTRIBUTES) 2))) SCALE))  (- (CADR POINT) 45.00) 0.0))
      (SETQ INS_PT1 (LIST (CAR INS_PT)  (+ (CADR POINT1) 15) 0.0))
      )
      (PROGN
      (SETQ INS_PT (LIST (+ (CAR POINT) (/ (ATOF (SUBSTR MAST_ATTRIBUTES (+ (VL-STRING-POSITION (ASCII "/") MAST_ATTRIBUTES) 2))) SCALE))  (- (CADR POINT) 157.00) 0.0))
      (SETQ INS_PT1 (LIST (CAR INS_PT)  (- (CADR POINT1) 15) 0.0))
      )
  )
  (COMMAND "INSERT" "OLC1" INS_PT "1" "0" )
  (MODIFY_ATTRIBUTES (ENTLAST) (SINGLE_ELE_LIST ACC_ATTRIBUTES 0)  (SINGLE_ELE_LIST ACC_ATTRIBUTES 1))
  (COMMAND "INSERT" "BWA_SCH" INS_PT1 "1" "0" )
  )
  )
  ;(INSERT_DYNAMIC_PROPERTIES (ENTLAST) (LIST "ACF1")  (LIST ACC_FLIP))
  ;(INSERT_ATTRIBUTES (ENTLAST) (LIST "MAST_COUNT1" "MAST_COUNT2")  (LIST ACC_FLIP))
  (SETQ I (+ I 1))
  )
)
