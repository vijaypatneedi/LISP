(DEFUN YARD_DATA_COLLECT2 (WPT1 WPT2 BLOCKNAME_LIST J K L / LIST1 I TEMP_ELE TEMP_LIST LIST2)

  (SETQ LIST1 (SINGLE_ELE_LIST (FILTER_LIST BLOCKNAME_LIST (DATA_COLLECT2 WPT1 WPT2 '((0 . "INSERT")) 2 -1)  0) 1))
  (SETQ I 0)
  (SETQ TEMP_ELE NIL)
  (SETQ TEMP_LIST NIL)
  (SETQ LIST2 NIL)
  (WHILE (< I (LENGTH LIST1))
    (SETQ TEMP_LIST (YARD_STRUCTURE_INFO (NTH I LIST1)))
  (SETQ TEMP_ELE (LIST (NTH 1 (ASSOC J  TEMP_LIST)) (NTH 1 (ASSOC K  TEMP_LIST)) (NTH 1 (ASSOC L  TEMP_LIST))))
  (SETQ LIST2 (CONS TEMP_ELE LIST2))
    (SETQ I (+ I 1))
    )
  (REVERSE LIST2)
)



(DEFUN YARD_DATA_COLLECT3 (LIST1 J K L / LIST1 I TEMP_ELE TEMP_LIST LIST2)
  (SETQ I 0)
  (SETQ TEMP_ELE NIL)
  (SETQ TEMP_LIST NIL)
  (SETQ LIST2 NIL)
  (WHILE (< I (LENGTH LIST1))
    (SETQ TEMP_LIST (YARD_STRUCTURE_INFO (NTH I LIST1)))
  (SETQ TEMP_ELE (LIST (NTH 1 (ASSOC J  TEMP_LIST)) (NTH 1 (ASSOC K  TEMP_LIST)) (NTH 1 (ASSOC L  TEMP_LIST))))
  (SETQ LIST2 (CONS TEMP_ELE LIST2))
    (SETQ I (+ I 1))
    )
  (REVERSE LIST2)
)



(DEFUN C:CREATE_WIRE_NUMBER ( / WPT1 WPT2 BWA_NUMBER ACA_NUMBER FA_NUMBER AEWA_NUMBER ANCHOR_ENTITIES BTB_ANCHOR_ENTITIES MAST_TTC ANCHOR_ENTITIES BTB_ANCHOR_ENTITIES UPSIDE_ANCHORS DNSIDE_ANCHORS UPSIDE_BTB_ANCHORS DNSIDE_BTB_ANCHORS UPSIDE_BWA_ANCHORS UPSIDE_ACA_ANCHORS DNSIDE_BWA_ANCHORS DNSIDE_ACA_ANCHORS UPSIDE_FA_ANCHORS UPSIDE_AEWA_ANCHORS DNSIDE_FA_ANCHORS DNSIDE_AEWA_ANCHORS )
  (SETQ WPT1 (GETPOINT "ENTER STARTING POINT IN LOP"))
  (SETQ WPT2 (GETPOINT "\n ENTER ENDING POINT IN LOP"))
  (SETQ BWA_NUMBER (GETINT "\n ENTER STARTING WIRE NUMBER FOR CONTACT/CATENARY WIRE"))
  (SETQ ACA_NUMBER (GETINT "\n ENTER STARTING WIRE NUMBER FOR ANTICREEP WIRE"))
  (SETQ FA_NUMBER (GETINT "\n ENTER STARTING WIRE NUMBER FOR FEEDER WIRE"))
  (SETQ AEWA_NUMBER (GETINT "\n ENTER STARTING WIRE NUMBER FOR ARIAL EARTH WIRE"))
  ;(SETQ ANCHOR_LIST (YARD_DATA_COLLECT WPT1 WPT2 '("ANCHOR") 1 3))
 (SETQ ANCHOR_ENTITIES (YARD_DATA_COLLECT WPT1 WPT2 '("ANCHOR") 1 5))
 (SETQ BTB_ANCHOR_ENTITIES (YARD_DATA_COLLECT WPT1 WPT2 '("BTB_ANC") 1 3))


  (SETQ MAST_TTC (YARD_DATA_COLLECT2 WPT1 WPT2 '("SINGLE_CANT_MAST" "DOUBLE_CANT_MAST" "TRIPLE_CANT_MAST" "TTC" "SS0" "SS1" "SS2" "SS3" "SS4") 1 3 5))
  

 (SETQ ANCHOR_ENTITIES  (BUILD_LIST (ENTITY_DFX (SINGLE_ELE_LIST ANCHOR_ENTITIES 0)  10 -1) (LIST 0 1)))
 (SETQ BTB_ANCHOR_ENTITIES  (BUILD_LIST (ENTITY_DFX (SINGLE_ELE_LIST BTB_ANCHOR_ENTITIES 0)  10 -1) (LIST 0 1)))


  
  (IF (/= ANCHOR_ENTITIES NIL) (SETQ ANCHOR_STRUCTURE_MAP_DATA (DATA_TO_STRUCTURE_MAP_SECTIONING ANCHOR_ENTITIES MAST_TTC 1 1)) (SETQ ANCHOR_START NIL))
  (IF (/= BTB_ANCHOR_ENTITIES NIL) (SETQ BTB_ANCHOR_STRUCTURE_MAP_DATA (DATA_TO_STRUCTURE_MAP_SECTIONING BTB_ANCHOR_ENTITIES MAST_TTC 1 1)) (SETQ ANCHOR_END NIL))

(SETQ UPSIDE_ANCHORS (FILTER_LIST (LIST "DN") ANCHOR_STRUCTURE_MAP_DATA 3))
(SETQ DNSIDE_ANCHORS (FILTER_LIST (LIST "UP") ANCHOR_STRUCTURE_MAP_DATA 3))
(SETQ UPSIDE_BTB_ANCHORS (FILTER_LIST (LIST "DN") BTB_ANCHOR_STRUCTURE_MAP_DATA 3))
(SETQ DNSIDE_BTB_ANCHORS (FILTER_LIST (LIST "UP") BTB_ANCHOR_STRUCTURE_MAP_DATA 3))
(SETQ UPSIDE_ANCHORS (ATTRIBUTES_FROM_ENTITIES (SINGLE_ELE_LIST UPSIDE_ANCHORS 0) "ANCHOR_TYPE1" 1))
(SETQ DNSIDE_ANCHORS (ATTRIBUTES_FROM_ENTITIES (SINGLE_ELE_LIST DNSIDE_ANCHORS 0) "ANCHOR_TYPE1" 1))
(SETQ UPSIDE_BTB_ANCHORS (ATTRIBUTES_FROM_ENTITIES (SINGLE_ELE_LIST UPSIDE_BTB_ANCHORS 0) "ANCHOR_TYPE1" 1))
(SETQ DNSIDE_BTB_ANCHORS (ATTRIBUTES_FROM_ENTITIES (SINGLE_ELE_LIST DNSIDE_BTB_ANCHORS 0) "ANCHOR_TYPE1" 1))

(SETQ UPSIDE_BWA_ANCHORS (SINGLE_ELE_LIST (FILTER_LIST (LIST "BWA" "FTA") UPSIDE_ANCHORS 1) 0))
(SETQ UPSIDE_ACA_ANCHORS (SINGLE_ELE_LIST (FILTER_LIST (LIST "ACA") UPSIDE_ANCHORS 1) 0))
(SETQ DNSIDE_BWA_ANCHORS (SINGLE_ELE_LIST (FILTER_LIST (LIST "BWA" "FTA") DNSIDE_ANCHORS 1) 0))
(SETQ DNSIDE_ACA_ANCHORS (SINGLE_ELE_LIST (FILTER_LIST (LIST "ACA") DNSIDE_ANCHORS 1) 0))


(SETQ UPSIDE_FA_ANCHORS (SINGLE_ELE_LIST (FILTER_LIST (LIST "FA") UPSIDE_BTB_ANCHORS 1) 0))
(SETQ UPSIDE_AEWA_ANCHORS (SINGLE_ELE_LIST (FILTER_LIST (LIST "AEWA") UPSIDE_BTB_ANCHORS 1) 0))
(SETQ DNSIDE_FA_ANCHORS (SINGLE_ELE_LIST (FILTER_LIST (LIST "FA") DNSIDE_BTB_ANCHORS 1) 0))
(SETQ DNSIDE_AEWA_ANCHORS (SINGLE_ELE_LIST (FILTER_LIST (LIST "AEWA") DNSIDE_BTB_ANCHORS 1) 0))

(SETQ UPSIDE_BWA_ANCHORS (YARD_DATA_COLLECT3 (SINGLE_ELE_LIST UPSIDE_BWA_ANCHORS 0) 1 5 3))
(SETQ UPSIDE_ACA_ANCHORS (YARD_DATA_COLLECT3 (SINGLE_ELE_LIST UPSIDE_ACA_ANCHORS 0) 1 5 3))
(SETQ DNSIDE_BWA_ANCHORS (YARD_DATA_COLLECT3 (SINGLE_ELE_LIST DNSIDE_BWA_ANCHORS 0) 1 5 3))
(SETQ DNSIDE_ACA_ANCHORS (YARD_DATA_COLLECT3 (SINGLE_ELE_LIST DNSIDE_ACA_ANCHORS 0) 1 5 3))

(SETQ UPSIDE_FA_ANCHORS (SINGLE_ELE_LIST (SORT_FUN (YARD_DATA_COLLECT3 (SINGLE_ELE_LIST UPSIDE_FA_ANCHORS 0) 1 5 3) 2 0) 0))
(SETQ UPSIDE_AEWA_ANCHORS (SINGLE_ELE_LIST (SORT_FUN (YARD_DATA_COLLECT3 (SINGLE_ELE_LIST UPSIDE_AEWA_ANCHORS 0) 1 5 3) 2 0) 0))
(SETQ DNSIDE_FA_ANCHORS (SINGLE_ELE_LIST (SORT_FUN (YARD_DATA_COLLECT3 (SINGLE_ELE_LIST DNSIDE_FA_ANCHORS 0) 1 5 3) 2 0) 0))
(SETQ DNSIDE_AEWA_ANCHORS (SINGLE_ELE_LIST (SORT_FUN (YARD_DATA_COLLECT3 (SINGLE_ELE_LIST DNSIDE_AEWA_ANCHORS 0) 1 5 3) 2 0) 0))

(BWA_NUMBERING_NORMAL UPSIDE_BWA_ANCHORS "UP" BWA_NUMBER)
(ACA_NUMBERING_NORMAL UPSIDE_ACA_ANCHORS "UP" ACA_NUMBER)
(BWA_NUMBERING_NORMAL DNSIDE_BWA_ANCHORS "DN" BWA_NUMBER)
(ACA_NUMBERING_NORMAL DNSIDE_ACA_ANCHORS "DN" ACA_NUMBER)

(AEWA/FA_NUMBERING_NORMAL UPSIDE_FA_ANCHORS "FA" "UP" FA_NUMBER)
(AEWA/FA_NUMBERING_NORMAL UPSIDE_AEWA_ANCHORS "AE" "UP" AEWA_NUMBER)
(AEWA/FA_NUMBERING_NORMAL DNSIDE_FA_ANCHORS "FA" "DN" FA_NUMBER)
(AEWA/FA_NUMBERING_NORMAL DNSIDE_AEWA_ANCHORS "AE" "DN" AEWA_NUMBER)

)

(DEFUN WIRE_NUMBERING ( LOCATION_LIST TRACK_TYPE / I TEMP_LIST BWA_LIST ACA_LIST AEWA_LIST FA_LIST )
  (SETQ I 0 TEMP_LIST NIL)
  (WHILE (< I (LENGTH LOCATION_LIST))
    (SETQ TEMP_LIST (CONS (LIST I (NTH I LOCATION_LIST)) TEMP_LIST))
    (SETQ I (+ I 1))
  )
  (SETQ TEMP_LIST (REVERSE TEMP_LIST))
  (SETQ BWA_LIST (BWA_NUMBERING (SORT_FUN (FILTER_LIST (LIST "BWA_START" "BWA_END") TEMP_LIST 1) 0 0) TRACK_TYPE))
  (SETQ ACA_LIST (ACA_NUMBERING (SORT_FUN (FILTER_LIST (LIST "ACA_START" "ACA_END") TEMP_LIST 1) 0 0) TRACK_TYPE))
  (SETQ AEWA_LIST (AEWA/FA_NUMBERING (SORT_FUN (FILTER_LIST (LIST "AEWA" "OLCAEWA" "DAEWA" "ACCAEWA") TEMP_LIST 1) 0 0) "AE" TRACK_TYPE))
  (SETQ FA_LIST (AEWA/FA_NUMBERING (SORT_FUN (FILTER_LIST (LIST "FA" "OLCFA" "DFA" "ACCFA") TEMP_LIST 1) 0 0) "FA" TRACK_TYPE))
  (SORT_FUN (MERGE_ANCHOR_LIST TEMP_LIST (APPEND BWA_LIST ACA_LIST AEWA_LIST FA_LIST)) 0 0)
)


(DEFUN BWA_NUMBERING_NORMAL ( BWA_LIST TRACK_TYPE NUMBER / BWA_NUMBERING1 BWA_START_LIST BWA_END_LIST I START_TEMP_LIST END_TEMP_LIST)
  (SETQ BWA_LIST (SORT_FUN BWA_LIST 2 0))
  (IF (= (NTH 1 (NTH 0 BWA_LIST)) "END") (SETQ BWA_NUMBERING1 (CDR BWA_LIST)) (SETQ BWA_NUMBERING1 BWA_LIST))
  (SETQ BWA_START_LIST (SORT_FUN (FILTER_LIST (LIST "START") BWA_NUMBERING1 1) 2 0))
  (SETQ BWA_END_LIST (CDR (SORT_FUN (FILTER_LIST (LIST "END") BWA_NUMBERING1 1) 2 0)))
  (SETQ I 0 START_TEMP_LIST NIL END_TEMP_LIST NIL)
  (IF (= TRACK_TYPE "UP") (SETQ J (+ NUMBER 1)) (SETQ J NUMBER))
  (IF (AND (/= BWA_START_LIST NIL) (/= BWA_END_LIST NIL))
  (PROGN
  (WHILE (< I (LENGTH BWA_START_LIST))
    (MODIFY_ATTRIBUTES   (NTH 0 (NTH I BWA_START_LIST)) (LIST "WIRE_RUN1") (LIST (STRCAT "W-" (RTOS J 2 0))))        
    (IF (/= (NTH I BWA_END_LIST) NIL)
    (MODIFY_ATTRIBUTES   (NTH 0 (NTH I BWA_END_LIST)) (LIST "WIRE_RUN1") (LIST (STRCAT "W-" (RTOS J 2 0))))
    )
    (SETQ I (+ I 1))
    (SETQ J (+ J 2))
  )
  )
  )
(APPEND START_TEMP_LIST END_TEMP_LIST)
)


(DEFUN ACA_NUMBERING_NORMAL ( ACA_LIST TRACK_TYPE NUMBER / ACA_NUMBERING1 ACA_START_LIST ACA_END_LIST I START_TEMP_LIST END_TEMP_LIST)
  (SETQ ACA_LIST (SORT_FUN ACA_LIST 2 0))
  (IF (= (NTH 1 (NTH 0 ACA_LIST)) "END") (SETQ ACA_NUMBERING1 (CDR ACA_LIST)) (SETQ ACA_NUMBERING1 ACA_LIST))
  (SETQ ACA_START_LIST (SORT_FUN (FILTER_LIST (LIST "START") ACA_NUMBERING1 1) 2 0))
  (SETQ ACA_END_LIST (SORT_FUN (FILTER_LIST (LIST "END") ACA_NUMBERING1 1) 2 0))
  (SETQ I 0)
  (IF (= TRACK_TYPE "UP") (SETQ J (+ NUMBER 1)) (SETQ J NUMBER))
  (WHILE (< I (LENGTH ACA_START_LIST))
    (MODIFY_ATTRIBUTES   (NTH 0 (NTH I ACA_START_LIST)) (LIST "WIRE_RUN1") (LIST (STRCAT "AC-" (RTOS J 2 0))))            
    (IF (/= (NTH I ACA_END_LIST) NIL)
    (MODIFY_ATTRIBUTES   (NTH 0 (NTH I ACA_END_LIST)) (LIST "WIRE_RUN1") (LIST (STRCAT "AC-" (RTOS J 2 0))))
    )
    (SETQ I (+ I 1))
    (SETQ J (+ J 2))
  )
(APPEND START_TEMP_LIST END_TEMP_LIST)
)




(DEFUN AEWA/FA_NUMBERING_NORMAL ( ANCHOR_LIST STRING TRACK_TYPE NUMBER / I J K TEMP_LIST)
(SETQ I 0 TEMP_LIST NIL)
(IF (= TRACK_TYPE "UP") (SETQ J (- NUMBER 1) K (+ NUMBER 1)) (SETQ J (- NUMBER 2) K NUMBER))
  (WHILE (< I (LENGTH ANCHOR_LIST))
    (IF (/= I 0)
      (MODIFY_ATTRIBUTES (NTH I ANCHOR_LIST) (LIST "WIRE_NO1" "WIRE_NO2") (LIST (STRCAT STRING "-" (RTOS J 2 0)) (STRCAT STRING "-" (RTOS K 2 0))))
      (MODIFY_ATTRIBUTES (NTH I ANCHOR_LIST) (LIST "WIRE_NO1" "WIRE_NO2") (LIST "NA-0" (STRCAT STRING "-" (RTOS K 2 0))))             
    )
    (SETQ I (+ I 1))
    (SETQ J (+ J 2))
    (SETQ K (+ K 2))
  )
(REVERSE TEMP_LIST)
)
