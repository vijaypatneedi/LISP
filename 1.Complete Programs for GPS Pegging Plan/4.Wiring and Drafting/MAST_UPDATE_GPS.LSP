(DEFUN C:UPDATE_MAST_GPS ( / )
  ;(SETQ WPT1 (GETPOINT "\n ENTER 1ST POINT OF POLYGON"))
  ;(SETQ WPT2 (GETPOINT "\n ENTER 2ND POINT OF POLYGON"))
  ;(SETQ WPT3 (GETPOINT "\n ENTER 3RD POINT OF POLYGON"))
  ;(SETQ WPT4 (GETPOINT "\n ENTER 4TH POINT OF POLYGON"))
  ;(SETQ BLOCKS_LIST (FORM_SSSET (SSGET "WP" (LIST WPT1 WPT2 WPT3 WPT4) (LIST (CONS 0 "INSERT")))))
  (SETQ BLOCKS_LIST (FORM_SSSET (SSGET "X" (LIST (CONS 0 "INSERT")))))
  (SETQ TRACK_ENTITY_UPTRACK (CAR(ENTSEL "\nSELECT TRACK ALIGNMENT FOR UP TRACK (DN LINE):")))
  (SETQ TRACK_ENTITY_DNTRACK (CAR(ENTSEL "\nSELECT TRACK ALIGNMENT FOR DN TRACK (UP LINE):")))
  (SETQ STARTING_POINT (GETPOINT "\nENTER STARTING POINT FOR UP TRACK (DN LINE):"))
  (SETQ STARTING_POINT_DN (GETPOINT "\nENTER STARTING POINT FOR DN TRACK (UP LINE):"))
  (SETQ BLOCK_NAME_LIST (EXTRACT_ENTITY_INFO2 BLOCKS_LIST))
  (SETQ ACC_LIST (FILTER_LIST (LIST "ACC") BLOCK_NAME_LIST 1))
  (SETQ OLC_LIST (FILTER_LIST (LIST "OLC") BLOCK_NAME_LIST 1))
  (SETQ TL_LIST (FILTER_LIST (LIST "TENSION_LENGTH") BLOCK_NAME_LIST 1))
  (SETQ ACC_LIST (BUILD_LIST (ENTITY_DFX (SINGLE_ELE_LIST ACC_LIST 0) 10 -1) (LIST 0 1)))
  (SETQ OLC_LIST (BUILD_LIST (ENTITY_DFX (SINGLE_ELE_LIST OLC_LIST 0) 10 -1) (LIST 0 1)))
  (SETQ TL_LIST  (BUILD_LIST (ENTITY_DFX (SINGLE_ELE_LIST TL_LIST 0)  10 -1) (LIST 0 1)))
  ;(COMMAND "BURST" (ENTLAST))
  (SETQ MAST_TTC (YARD_DATA_COLLECT_GPS BLOCKS_LIST '("SINGLE_CANT_MAST" "DOUBLE_CANT_MAST" "TRIPLE_CANT_MAST" "TTC" "SS0" "SS1" "SS2" "SS3" "SS4") 1 3))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  ;(SETQ ANCHOR_LIST (YARD_DATA_COLLECT WPT1 WPT2 '("ANCHOR") 1 3))
 (SETQ ANCHOR_ENTITIES (YARD_DATA_COLLECT_GPS BLOCKS_LIST '("ANCHOR") 1 5))
 (SETQ BTB_ANCHOR_ENTITIES (YARD_DATA_COLLECT_GPS BLOCKS_LIST '("BTB_ANC") 1 3))
 (SETQ ANCHOR_START (FILTER_LIST '("START") ANCHOR_ENTITIES 1))
 (SETQ ANCHOR_END (FILTER_LIST '("END") ANCHOR_ENTITIES 1))
 (SETQ MULTIPLE_CANT_MASTS (SINGLE_ELE_LIST (YARD_DATA_COLLECT_GPS BLOCKS_LIST '("DOUBLE_CANT_MAST" "TRIPLE_CANT_MAST" "SS2" "SS3") 1 3) 0))
 (SETQ MAST_UP (FILTER_LIST '("UP") MAST_TTC_DIR 1))
 (SETQ MAST_DN (FILTER_LIST '("DN") MAST_TTC_DIR 1))
  
 (SETQ ANCHOR_START  (BUILD_LIST (ENTITY_DFX (SINGLE_ELE_LIST ANCHOR_START 0)  10 -1) (LIST 0 1)))
 (SETQ ANCHOR_END  (BUILD_LIST (ENTITY_DFX (SINGLE_ELE_LIST ANCHOR_END 0)  10 -1) (LIST 0 1)))

  
  (IF (/= ANCHOR_START NIL) (SETQ ANCHOR_START_STRUCTURE_MAP_DATA (DATA_TO_STRUCTURE_MAP_SECTIONING ANCHOR_START MAST_TTC 1 1)) (SETQ ANCHOR_START NIL))
  (IF (/= ANCHOR_END NIL) (SETQ ANCHOR_END_STRUCTURE_MAP_DATA (DATA_TO_STRUCTURE_MAP_SECTIONING ANCHOR_END MAST_TTC 1 1)) (SETQ ANCHOR_END NIL))
  
  (IF (/= ACC_LIST NIL) (SETQ ACC_STRUCTURE_MAP_DATA (DATA_TO_STRUCTURE_MAP_SECTIONING ACC_LIST MAST_TTC 1 1)) (SETQ ACC_STRUCTURE_MAP_DATA NIL))



  
 (SETQ MAST_UP  (ADD_LISTS (BUILD_LIST (ENTITY_DFX (SINGLE_ELE_LIST MAST_UP 0)  10 -1) (LIST 0 1)) (N_ELE_LIST "UP" (LENGTH MAST_UP))))
 (SETQ MAST_DN  (ADD_LISTS (BUILD_LIST (ENTITY_DFX (SINGLE_ELE_LIST MAST_DN 0)  10 -1) (LIST 0 1)) (N_ELE_LIST "DN" (LENGTH MAST_DN))))

  (IF (/= BTB_ANCHOR_ENTITIES NIL) (SETQ BTB_ANCHOR_STRUCTURE_MAP_DATA_TOTAL (DATA_TO_STRUCTURE_MAP_SECTIONING BTB_ANCHOR_ENTITIES (APPEND MAST_UP MAST_DN) 1 1)) (SETQ BTB_ANCHOR_ENTITIES NIL))
  (SETQ BTB_ANCHOR_STRUCTURE_MAP_DATA_TOTAL (BUILD_LIST (SORT_ENTITIES_ALONG_CURVE1 TRACK_ENTITY_UPTRACK (ADD_LISTS BTB_ANCHOR_STRUCTURE_MAP_DATA_TOTAL (SINGLE_ELE_LIST (ENTITY_DFX (SINGLE_ELE_LIST BTB_ANCHOR_STRUCTURE_MAP_DATA_TOTAL 0)  10 -1) 1)) (LIST 1 STARTING_POINT) 1 1) (LIST 0 1 3)))
  (SETQ B225_LIST (APPEND (SINGLE_ELE_LIST ANCHOR_START_STRUCTURE_MAP_DATA 1) (SINGLE_ELE_LIST ANCHOR_END_STRUCTURE_MAP_DATA 1) (SINGLE_ELE_LIST ACC_STRUCTURE_MAP_DATA 1) (SINGLE_ELE_LIST BTB_ANCHOR_STRUCTURE_MAP_DATA_TOTAL 1)))
  (SETQ B200_LIST (SINGLE_ELE_LIST (FILTER_LIST1 B225_LIST MAST_TTC 0) 0))
  (SETQ ACC_LIST (SINGLE_ELE_LIST ACC_STRUCTURE_MAP_DATA 1))
  (SETQ I 0)
  (WHILE (< I (LENGTH B225_LIST))
    (MODIFY_ATTRIBUTES
      (NTH I B225_LIST)
      (LIST "MAST_TYPE1")
      (LIST "B-225(S)")
    )
    (SETQ I (+ I 1))
  )

  (SETQ I 0)
  (WHILE (< I (LENGTH B200_LIST))
    (MODIFY_ATTRIBUTES
      (NTH I B200_LIST)
      (LIST "MAST_TYPE1")
      (LIST "B-200(S)")
    )
    (SETQ I (+ I 1))
  )

  (SETQ I 0)
  (WHILE (< I (LENGTH ACC_LIST))
    (MODIFY_ATTRIBUTES
      (NTH I ACC_LIST)
      (LIST "ACC")
      (LIST "1")
    )
    (SETQ I (+ I 1))
  )
  (SETQ I 0)
  (WHILE (< I (LENGTH MULTIPLE_CANT_MASTS))
    (MODIFY_ATTRIBUTES
      (NTH I MULTIPLE_CANT_MASTS)
      (LIST "MAST_TYPE1")
      (LIST "B-225(S)")
    )
    (SETQ I (+ I 1))
  )
)
