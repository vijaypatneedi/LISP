(DEFUN C:GENERATE_CSD ( / )
   (SETQ BLOCKS_LIST (FORM_SSSET (SSGET "X" (LIST (CONS 0 "INSERT")))))
   (SETQ BLOCK_NAME_LIST (EXTRACT_ENTITY_INFO2 BLOCKS_LIST))
   (SETQ ENT_LIST (SINGLE_ELE_LIST (FILTER_LIST (LIST "SINGLE_CANT_MAST" "DOUBLE_CANT_MAST" "TRIPLE_CANT_MAST" "TTC" "SS0" "SS1" "SS2" "SS3" "SS4") BLOCK_NAME_LIST 1) 0))
   (SETQ STARTING_MAST (CAR(ENTSEL "N/ SELECT STARTING MAST")))
   (SETQ TRACK_CENTER (CAR(ENTSEL "N/ SELECT TRACK CENTER")))
   (SETQ STARTING_CELL (GETSTRING "N/ ENTER STARTING CELL"))
   ;(SETQ ENT_LIST (FORM_SSSET SSSET))
   (SETQ ENT_LIST (EXTRACT_ENTITY_INFO ENT_LIST 1 3))
   (SETQ ENT_LIST (SORT_MASTS ENT_LIST STARTING_MAST))
    (SETQ DETAILS_TO_PRINT (EXTRACT_CSD_DATA_CP204 (SINGLE_ELE_LIST ENT_LIST 0)))
    (PUTCELLSHEET "Sheet1" (COLUMN+N STARTING_CELL 0) (SINGLE_ELE_LIST DETAILS_TO_PRINT 0))
    (PUTCELLSHEET "Sheet1" (COLUMN+N STARTING_CELL 1) (SINGLE_ELE_LIST DETAILS_TO_PRINT 1))
    (PUTCELLSHEET "Sheet1" (COLUMN+N STARTING_CELL 2) (SINGLE_ELE_LIST DETAILS_TO_PRINT 2))
    (PUTCELLSHEET "Sheet1" (COLUMN+N STARTING_CELL 3) (SINGLE_ELE_LIST DETAILS_TO_PRINT 3))
    (PUTCELLSHEET "Sheet1" (COLUMN+N STARTING_CELL 4) (SINGLE_ELE_LIST DETAILS_TO_PRINT 4))
    (PUTCELLSHEET "Sheet1" (COLUMN+N STARTING_CELL 5) (SINGLE_ELE_LIST DETAILS_TO_PRINT 5))
    (PUTCELLSHEET "Sheet1" (COLUMN+N STARTING_CELL 6) (SINGLE_ELE_LIST DETAILS_TO_PRINT 6))
    (PUTCELLSHEET "Sheet1" (COLUMN+N STARTING_CELL 7) (SINGLE_ELE_LIST DETAILS_TO_PRINT 7))
     (PUTCELLSHEET "Sheet1" (COLUMN+N STARTING_CELL 8) (SINGLE_ELE_LIST DETAILS_TO_PRINT 8))
    (PUTCELLSHEET "Sheet1" (COLUMN+N STARTING_CELL 9) (SINGLE_ELE_LIST DETAILS_TO_PRINT 9))
    (PUTCELLSHEET "Sheet1" (COLUMN+N STARTING_CELL 10) (SINGLE_ELE_LIST DETAILS_TO_PRINT 10))
    (PUTCELLSHEET "Sheet1" (COLUMN+N STARTING_CELL 11) (SINGLE_ELE_LIST DETAILS_TO_PRINT 11))
    (PUTCELLSHEET "Sheet1" (COLUMN+N STARTING_CELL 12) (SINGLE_ELE_LIST DETAILS_TO_PRINT 12))
    (PUTCELLSHEET "Sheet1" (COLUMN+N STARTING_CELL 13) (SINGLE_ELE_LIST DETAILS_TO_PRINT 13))
    (PUTCELLSHEET "Sheet1" (COLUMN+N STARTING_CELL 14) (SINGLE_ELE_LIST DETAILS_TO_PRINT 14))
    (PUTCELLSHEET "Sheet1" (COLUMN+N STARTING_CELL 15) (SINGLE_ELE_LIST DETAILS_TO_PRINT 15))
     (PUTCELLSHEET "Sheet1" (COLUMN+N STARTING_CELL 16) (SINGLE_ELE_LIST DETAILS_TO_PRINT 16))
    (PUTCELLSHEET "Sheet1" (COLUMN+N STARTING_CELL 17) (SINGLE_ELE_LIST DETAILS_TO_PRINT 17))
    (PUTCELLSHEET "Sheet1" (COLUMN+N STARTING_CELL 18) (SINGLE_ELE_LIST DETAILS_TO_PRINT 18))
    (PUTCELLSHEET "Sheet1" (COLUMN+N STARTING_CELL 19) (SINGLE_ELE_LIST DETAILS_TO_PRINT 19))
    (PUTCELLSHEET "Sheet1" (COLUMN+N STARTING_CELL 20) (SINGLE_ELE_LIST DETAILS_TO_PRINT 20))
    (PUTCELLSHEET "Sheet1" (COLUMN+N STARTING_CELL 21) (SINGLE_ELE_LIST DETAILS_TO_PRINT 21))
    (PUTCELLSHEET "Sheet1" (COLUMN+N STARTING_CELL 22) (SINGLE_ELE_LIST DETAILS_TO_PRINT 22))
    (PUTCELLSHEET "Sheet1" (COLUMN+N STARTING_CELL 23) (SINGLE_ELE_LIST DETAILS_TO_PRINT 23))
    (PUTCELLSHEET "Sheet1" (COLUMN+N STARTING_CELL 24) (SINGLE_ELE_LIST DETAILS_TO_PRINT 24))
    (PUTCELLSHEET "Sheet1" (COLUMN+N STARTING_CELL 25) (SINGLE_ELE_LIST DETAILS_TO_PRINT 25))
    (PUTCELLSHEET "Sheet1" (COLUMN+N STARTING_CELL 26) (SINGLE_ELE_LIST DETAILS_TO_PRINT 26))
    (PUTCELLSHEET "Sheet1" (COLUMN+N STARTING_CELL 27) (SINGLE_ELE_LIST DETAILS_TO_PRINT 27))
    (PUTCELLSHEET "Sheet1" (COLUMN+N STARTING_CELL 28) (SINGLE_ELE_LIST DETAILS_TO_PRINT 28))
    (PUTCELLSHEET "Sheet1" (COLUMN+N STARTING_CELL 29) (SINGLE_ELE_LIST DETAILS_TO_PRINT 29))
)



(DEFUN C:LOAD_EXCEL_GPS ( / )
  (OPENEXCEL (FINDFILE "SPANEXTRACT.XLSX") "Sheet1" T)
)

(DEFUN C:LOAD_OBSTRUCTION_FILE ( / )
  (OPENEXCEL (FINDFILE (GETFILED "SELECT OBSTRUCTION FILE" "" "" 8)) "Sheet1" T)
)

(DEFUN EXTRACT_CSD_DATA_CP204 ( ENT_LIST  / ENT_LIST I TEMP_CHAINAGE TEMP_EFFNAME TEMP_SPAN FINAL_LIST)

  (SETQ I 0 TEMP_CHAINAGE NIL TEMP_EFFNAME NIL TEMP_SPAN NIL FINAL_LIST NIL)
  (WHILE (< I (LENGTH ENT_LIST))
    (SETQ TEMP_NUMBER (NTH 0 (SINGLE_ELE_LIST (EXTRACT_ATTRIBUTES (NTH I ENT_LIST) (LIST "MAST_NUMBER1" ) 1) 1)))
    (SETQ TEMP_CHAINAGE (NTH 0 (SINGLE_ELE_LIST (EXTRACT_ATTRIBUTES (NTH I ENT_LIST) (LIST "CHAINAGE1" ) 1) 1)))
    (SETQ TEMP_FDN_TYPE (NTH 0 (SINGLE_ELE_LIST (EXTRACT_ATTRIBUTES (NTH I ENT_LIST) (LIST "FOUNDATION_TYPE1" ) 1) 1)))
    (SETQ TEMP_MAST (NTH 0 (SINGLE_ELE_LIST (EXTRACT_ATTRIBUTES (NTH I ENT_LIST) (LIST "MAST_TYPE1" ) 1) 1)))
    (SETQ TEMP_IMP (NTH 0 (SINGLE_ELE_LIST (EXTRACT_ATTRIBUTES (NTH I ENT_LIST) (LIST "IMPLANTATION1" ) 1) 1)))
    
    (SETQ TEMP_RADIUS/SE (NTH 0 (SINGLE_ELE_LIST (EXTRACT_ATTRIBUTES (NTH I ENT_LIST) (LIST "RADIUS/SUPER_ELEVATION" ) 1) 1)))
    (SETQ TEMP_RADIUS (SUBSTR TEMP_RADIUS/SE 1 (VL-STRING-POSITION (ASCII "/") TEMP_RADIUS/SE)))
    (SETQ TEMP_SE (SUBSTR TEMP_RADIUS/SE (+ (VL-STRING-POSITION (ASCII "/") TEMP_RADIUS/SE) 2)))
    
    (SETQ TEMP_SPAN (NTH 0 (SINGLE_ELE_LIST (EXTRACT_ATTRIBUTES (NTH I ENT_LIST) (LIST "SPAN1" ) 1) 1)))
    
    (SETQ TEMP_FL (NTH 0 (SINGLE_ELE_LIST (EXTRACT_ATTRIBUTES (NTH I ENT_LIST) (LIST "DUMMY_VARIABLE2" ) 1) 1)))

    (SETQ TEMP_STEP_DISTANCE/EL (NTH 0 (SINGLE_ELE_LIST (EXTRACT_ATTRIBUTES (NTH I ENT_LIST) (LIST "STEP_DISTANCE/EMBEDDED_LENGTH" ) 1) 1)))
    (SETQ TEMP_STEP_DISTANCE (SUBSTR TEMP_STEP_DISTANCE/EL 1 (VL-STRING-POSITION (ASCII "/") TEMP_STEP_DISTANCE/EL)))
    (SETQ TEMP_EL (SUBSTR TEMP_STEP_DISTANCE/EL (+ (VL-STRING-POSITION (ASCII "/") TEMP_STEP_DISTANCE/EL) 2)))

    (SETQ TEMP_RD (NTH 0 (SINGLE_ELE_LIST (EXTRACT_ATTRIBUTES (NTH I ENT_LIST) (LIST "RD1" ) 1) 1)))

    (SETQ TEMP_SB/ED (NTH 0 (SINGLE_ELE_LIST (EXTRACT_ATTRIBUTES (NTH I ENT_LIST) (LIST "STEP_DISTANCE/EMBEDDED_LENGTH" ) 1) 1)))
    
    (SETQ FLIP (NTH 1 (NTH 0 (GET_DYNAMIC_PROPERTIES (NTH I ENT_LIST) '("STF1")))))
    
    (SETQ ROTATION (VLAX-GET-PROPERTY (VLAX-ENAME->VLA-OBJECT (NTH I ENT_LIST)) 'ROTATION))
    (SETQ TEMP_CO-ORDINATES (CDR (ASSOC 10 (ENTGET (NTH I ENT_LIST)))))
    (IF (= FLIP 0)
     (SETQ TEMP_CO-ORDINATES (MAPCAR 'RTOS (POLAR TEMP_CO-ORDINATES (+ (* 1 (/ PI 2)) ROTATION) (+ (- (ATOF TEMP_IMP) 3.00) 0.15))) TEMP_LINE "Dn Line")
     (SETQ TEMP_CO-ORDINATES (MAPCAR 'RTOS (POLAR TEMP_CO-ORDINATES (+ (* 3 (/ PI 2)) ROTATION) (+ (- (ATOF TEMP_IMP) 3.00) 0.15))) TEMP_LINE "Up Line")
    )
    
    (SETQ X-CORDINATE (NTH 0 TEMP_CO-ORDINATES))
    (SETQ Y-CORDINATE (NTH 1 TEMP_CO-ORDINATES))

    (SETQ X_Y (STRCAT "( " X-CORDINATE "," Y-CORDINATE ")"))
    
    (SETQ FINAL_LIST (CONS (LIST TEMP_NUMBER TEMP_CHAINAGE TEMP_SPAN TEMP_LINE TEMP_IMP TEMP_RADIUS "" TEMP_FL TEMP_MAST "10" TEMP_STEP_DISTANCE TEMP_EL "7.75" TEMP_RD "NORMAL / >1.3" "" "" "" "" "" "" TEMP_FDN_TYPE TEMP_SB/ED X_Y "" "" "" "" TEMP_SE  ) FINAL_LIST))
    (SETQ I (+ I 1))
  )
  (REVERSE FINAL_LIST)
  
)
