(DEFUN C:COUNT_STYLES ( / )
 (SETQ WPT1 (GETPOINT "ENTER STARTING POINT IN LOP"))
 (SETQ WPT2 (GETPOINT "\n ENTER ENDING POINT IN LOP"))
 (SETQ STARTING_CELL (GETSTRING "\nEnter starting cell"))
 (SETQ BLOCKS_LIST (FORM_SSSET (SSGET "W" WPT1 WPT2 (LIST (CONS 0 "INSERT")))))
 (SETQ BLOCK_NAME_LIST (EXTRACT_ENTITY_INFO2 BLOCKS_LIST))
 (SETQ CANTILEVER_LIST (FILTER_LIST (LIST "SINGLE_CANT_MAST"  "SINGLE_CANT_DA" "DOUBLE_CANT_MAST"  "DOUBLE_CANT_DA" "TRIPLE_CANT_MAST"  "TRIPLE_CANT_DA" "SINGLE_CANT_UPRIGHT" "DOUBLE_CANT_UPRIGHT" "TRIPLE_CANT_UPRIGHT" "SS1" "SS2" "SS3") BLOCK_NAME_LIST 1))
 (SETQ ANCHOR_LIST (FILTER_LIST (LIST "ANCHOR") BLOCK_NAME_LIST 1))
 (SETQ BTB_ANCHOR_LIST (FILTER_LIST (LIST "BTB_ANC") BLOCK_NAME_LIST 1))
 (SETQ CANTILEVER_LIST (ATTRIBUTES_FROM_ENTITIES CANTILEVER_LIST "WIRE_SYSTEM" 0))
 (SETQ CANTILEVER_LIST (SINGLE_ELE_LIST (FILTER_LIST (LIST "107") CANTILEVER_LIST 2) 0))
 (SETQ CANTILEVER_LIST_WIRE_NATURE1 (ATTRIBUTES_FROM_ENTITIES CANTILEVER_LIST "WIRE_NATURE1" 0))
 (SETQ CANTILEVER_LIST_WIRE_NATURE2 (ATTRIBUTES_FROM_ENTITIES CANTILEVER_LIST "WIRE_NATURE2" 0))
 (SETQ CANTILEVER_LIST_WIRE_NATURE3 (ATTRIBUTES_FROM_ENTITIES CANTILEVER_LIST "WIRE_NATURE3" 0))
 (SETQ CANTILEVER_LIST_WIRE_NATURE (APPEND CANTILEVER_LIST_WIRE_NATURE1 CANTILEVER_LIST_WIRE_NATURE2 CANTILEVER_LIST_WIRE_NATURE3))
 (SETQ CANTILEVER_LIST_ACC (ATTRIBUTES_FROM_ENTITIES CANTILEVER_LIST "ACC" 0))
 (SETQ CANTILEVER_LIST_WIRE_NATURE (REMOVE_NIL CANTILEVER_LIST_WIRE_NATURE))
 (SETQ CANTILEVER_LIST_ACC (REMOVE_NIL CANTILEVER_LIST_ACC))
 (SETQ CANT_STYLE_LIST (LIST (LIST "IN RUN PULL OFF" (/ (LENGTH (FILTER_LIST (LIST "IR") CANTILEVER_LIST_WIRE_NATURE 1)) 2)) (LIST "IN RUN PUSH OFF" (- (LENGTH (FILTER_LIST (LIST "IR") CANTILEVER_LIST_WIRE_NATURE 1)) (/ (LENGTH (FILTER_LIST (LIST "IR") CANTILEVER_LIST_WIRE_NATURE 1)) 2)))
       (LIST "LSW PULL OFF" (/ (LENGTH (FILTER_LIST (LIST "LSW") CANTILEVER_LIST_WIRE_NATURE 1)) 2)) (LIST "LSW PUSH OFF" (- (LENGTH (FILTER_LIST (LIST "LSW") CANTILEVER_LIST_WIRE_NATURE 1)) (/ (LENGTH (FILTER_LIST (LIST "LSW") CANTILEVER_LIST_WIRE_NATURE 1)) 2)))
       (LIST "OOR" (LENGTH (FILTER_LIST (LIST "OOR") CANTILEVER_LIST_WIRE_NATURE 1)))
 ))
 (SETQ ACC_CANT_STYLE_LIST (LIST (LIST "ACC PULL OFF" (/ (LENGTH (FILTER_LIST (LIST "1") CANTILEVER_LIST_ACC 1)) 2)) (LIST "ACC PUSH OFF" (- (LENGTH (FILTER_LIST (LIST "1") CANTILEVER_LIST_ACC 1)) (/ (LENGTH (FILTER_LIST (LIST "1") CANTILEVER_LIST_ACC 1)) 2)))))


  (SETQ ANCHOR_LIST (APPEND (ATTRIBUTES_FROM_ENTITIES ANCHOR_LIST "WIRE_SYSTEM" 0) (ATTRIBUTES_FROM_ENTITIES BTB_ANCHOR_LIST "WIRE_SYSTEM1" 0)))
 (SETQ ANCHOR_LIST (SINGLE_ELE_LIST (FILTER_LIST (LIST "107") ANCHOR_LIST 2) 0))
 (SETQ ANCHOR_NATURE_LIST (ATTRIBUTES_FROM_ENTITIES ANCHOR_LIST "ANCHOR_NATURE1" 0))
 (SETQ ANCHOR_TYPE_LIST (ATTRIBUTES_FROM_ENTITIES ANCHOR_NATURE_LIST "ANCHOR_TYPE1" 0))
 (SETQ STANDARD_TERMINATIONS (FILTER_LIST (LIST "STD") ANCHOR_TYPE_LIST 1) LSW_TERMINATIONS (FILTER_LIST (LIST "LSW") ANCHOR_TYPE_LIST 1))
 

 (SETQ ANCHOR_LIST2 (ATTRIBUTES_FROM_ENTITIES BTB_ANCHOR_LIST "WIRE_SYSTEM2" 0))
 (SETQ ANCHOR_LIST2 (SINGLE_ELE_LIST (FILTER_LIST (LIST "107") ANCHOR_LIST2 2) 0))
 (SETQ ANCHOR_NATURE_LIST2 (ATTRIBUTES_FROM_ENTITIES ANCHOR_LIST2 "ANCHOR_NATURE2" 0))
 (SETQ ANCHOR_TYPE_LIST2 (ATTRIBUTES_FROM_ENTITIES ANCHOR_LIST2 "ANCHOR_TYPE2" 0))
 (SETQ STANDARD_TERMINATIONS2 (FILTER_LIST (LIST "STD") ANCHOR_TYPE_LIST2 1) LSW_TERMINATIONS2 (FILTER_LIST (LIST "LSW") ANCHOR_TYPE_LIST2 1))
 

(SETQ ANCHOR_STYLE_LIST (LIST (LIST "BWA STANDARD TERMINATIONS" (+ (LENGTH (FILTER_LIST (LIST "BWA" "BWA(DMA)") STANDARD_TERMINATIONS 2)) (LENGTH (FILTER_LIST (LIST "BWA" "BWA(DMA)") STANDARD_TERMINATIONS2 2))))
			      (LIST "FTA STANDARD TERMINATIONS" (+ (LENGTH (FILTER_LIST (LIST "FTA" "FTA(DMA)") STANDARD_TERMINATIONS 2)) (LENGTH (FILTER_LIST (LIST "FTA" "FTA(DMA)") STANDARD_TERMINATIONS2 2))))
			      (LIST "ACA STANDARD TERMINATIONS" (+ (LENGTH (FILTER_LIST (LIST "ACA" "ACA(DMA)") STANDARD_TERMINATIONS 2)) (LENGTH (FILTER_LIST (LIST "ACA" "ACA(DMA)") STANDARD_TERMINATIONS2 2))))
	                      (LIST "BWA LSW TERMINATIONS" (+ (LENGTH (FILTER_LIST (LIST "BWA" "BWA(DMA)") LSW_TERMINATIONS 2)) (LENGTH (FILTER_LIST (LIST "BWA" "BWA(DMA)") LSW_TERMINATIONS2 2))))
			      (LIST "FTA LSW TERMINATIONS" (+ (LENGTH (FILTER_LIST (LIST "FTA" "FTA(DMA)") LSW_TERMINATIONS 2)) (LENGTH (FILTER_LIST (LIST "FTA" "FTA(DMA)") LSW_TERMINATIONS2 2))))
			      (LIST "ACA LSW TERMINATIONS" (+ (LENGTH (FILTER_LIST (LIST "ACA" "ACA(DMA)") LSW_TERMINATIONS 2)) (LENGTH (FILTER_LIST (LIST "ACA" "ACA(DMA)") LSW_TERMINATIONS2 2))))))

(SETQ GUY_ROD_STYLE_LIST (LIST (LIST "GUY ROD STYLE 1" (LENGTH (FILTER_LIST (LIST "BWA" "FTA" "ACA" ) (APPEND ANCHOR_TYPE_LIST ANCHOR_TYPE_LIST2) 2)))
                               (LIST "GUY ROD STYLE 3" (LENGTH (FILTER_LIST (LIST "BWA(DMA)" "FTA(DMA)" "ACA(DMA)" ) (APPEND ANCHOR_TYPE_LIST ANCHOR_TYPE_LIST2) 2)))))
   
 (SETQ FINAL_STYLES (APPEND CANT_STYLE_LIST ACC_CANT_STYLE_LIST ANCHOR_STYLE_LIST GUY_ROD_STYLE_LIST))
 (PUTCELLSHEET "Sheet1" (COLUMN+N STARTING_CELL 0) (SINGLE_ELE_LIST FINAL_STYLES 0))
 (PUTCELLSHEET "Sheet1" (COLUMN+N STARTING_CELL 1) (SINGLE_ELE_LIST FINAL_STYLES 1))
)


(DEFUN REMOVE_NIL (LIST1 / I FINAL_LIST)
  (SETQ I 0)
  (WHILE (< I (LENGTH LIST1))
    (IF (/= (NTH I LIST1) NIL) (SETQ FINAL_LIST (CONS (NTH I LIST1) FINAL_LIST)))
    (SETQ I (+ I 1))
  )
(REVERSE FINAL_LIST)
)
