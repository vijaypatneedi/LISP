(DEFUN C:KM_STONE ( / WPT1 NUMBER KM BLOCKS_LIST BLOCK_NAME_LIST KM_STONE_LIST I)
 (SETQ WPT1 (GETPOINT "ENTER STARTING POINT IN LOP"))
 (SETQ NUMBER (GETINT "\n ENTER KM COUNT"))
 (SETQ KM (GETSTRING "\n ENTER STARTING KM IN LOP"))
 (SETQ KM_STONE_LIST (INSERT_KM_STONE NUMBER WPT1))
 (SETQ I 0)
 (WHILE (< I (LENGTH KM_STONE_LIST))
  (MODIFY_ATTRIBUTES (NTH 0 (NTH I KM_STONE_LIST)) (LIST "KM" "LEFT_KM" "RIGHT_KM") (LIST (STRCAT "%%UKM:" KM) (STRCAT (ITOA (- (ATOI KM) 1)) "/1000.00" ) (STRCAT (ITOA (ATOI KM)) "/0000.00" )))
  (SETQ KM (ITOA (+ (ATOI KM) 1)))
  (SETQ I (+ I 1))
 )
)



(DEFUN INSERT_KM_STONE ( NUMBER STARTING_POINT / I FINAL_LIST )
  
(SETQ I 0 FINAL_LIST NIL)
  (WHILE (< I NUMBER)
    (COMMAND "INSERT" "KM_NEW" STARTING_POINT   "1" "0" )
    (SETQ FINAL_LIST (CONS (LIST (ENTLAST) STARTING_POINT) FINAL_LIST))
    (SETQ STARTING_POINT (LIST (+ (CAR STARTING_POINT) 1000) (CADR STARTING_POINT) 0.0))
    (SETQ I (+ I 1))
  )
(REVERSE FINAL_LIST)
)


(DEFUN C:PRINT_OBSTRUCTIONS ( / START_CELL END_CELL WPT1 WPT2 OFFSETS BLOCKS_LIST BLOCK_NAME_LIST KM_STONE_LIST KMLIST CHAINAGE_LIST OBSTRUCTION_LIST DIRECTION_LIST TOTAL_LIST KM_STONE_COORDINATES OFFSETS UP_OFFSET CENTER_OFFSET DN_OFFSET)
(SETQ START_CELL (GETSTRING "\N ENTER STARTING CELL"))
 (SETQ END_CELL (GETSTRING "\N ENTER ENDING CELL"))
 (SETQ WPT1 (GETPOINT "ENTER STARTING POINT IN LOP"))
 (SETQ WPT2 (GETPOINT "\n ENTER ENDING POINT IN LOP"))
 (SETQ OFFSETS (FORM_SSSET (SSGET)))
 (SETQ BLOCKS_LIST (FORM_SSSET (SSGET "W" WPT1 WPT2 (LIST (CONS 0 "INSERT")))))
 (SETQ BLOCK_NAME_LIST (EXTRACT_ENTITY_INFO2 BLOCKS_LIST))
 (SETQ KM_STONE_LIST (FILTER_LIST (LIST "KM_NEW" "KM_STONE" "KMNEW" "KMSTONE") BLOCK_NAME_LIST 1))
 (SETQ KM_STONE_LIST (SORT_FUN (ENTITY_DFX (SINGLE_ELE_LIST KM_STONE_LIST 0) 10 -1) 1 0))
 (SETQ KMLIST (getCellsrow/column "Sheet1" (STRCAT (COLUMN+N START_CELL 0) ":" (COLUMN+N END_CELL 0))))
 (SETQ CHAINAGE_LIST (getCellsrow/column "Sheet1" (STRCAT (COLUMN+N START_CELL 1) ":" (COLUMN+N END_CELL 1))))
 (SETQ OBSTRUCTION_LIST (getCellsrow/column "Sheet1" (STRCAT (COLUMN+N START_CELL 2) ":" (COLUMN+N END_CELL 2))))
 (SETQ DIRECTION_LIST (getCellsrow/column "Sheet1" (STRCAT (COLUMN+N START_CELL 3) ":" (COLUMN+N END_CELL 3))))
 (SETQ WIDTH_LIST (getCellsrow/column "Sheet1" (STRCAT (COLUMN+N START_CELL 4) ":" (COLUMN+N END_CELL 4))))
 (SETQ NUMBER_LIST (getCellsrow/column "Sheet1" (STRCAT (COLUMN+N START_CELL 5) ":" (COLUMN+N END_CELL 5))))
 (SETQ TOTAL_LIST (ADD_LISTS (ADD_LISTS (ADD_LISTS (ADD_LISTS1 KMLIST CHAINAGE_LIST) (ADD_LISTS1 OBSTRUCTION_LIST DIRECTION_LIST)) WIDTH_LIST) NUMBER_LIST))
 (SETQ KM_STONE_COORDINATES (GET_KM_STONE_COORDINATES KM_STONE_LIST))
 (SETQ OFFSETS (REVERSE (SORT_FUN (ENTITY_DFX OFFSETS 10 -1) 1 1)))
 (SETQ UP_OFFSET (NTH 1 (NTH 0 OFFSETS)))
 (SETQ TR_OFFSET1 (NTH 1 (NTH 1 OFFSETS)))
 (SETQ TR_OFFSET2 (NTH 1 (NTH 2 OFFSETS)))
 (SETQ DN_OFFSET (NTH 1 (NTH 3 OFFSETS)))
 (INSERT_OBSTRUCTIONS TOTAL_LIST KM_STONE_COORDINATES UP_OFFSET TR_OFFSET1 TR_OFFSET2  DN_OFFSET)
 (COMMAND "REGEN")
 )

(DEFUN GET_KM_STONE_COORDINATES (KM_STONE_LIST / I ATTR_LIST KM KM_POINT_LIST)
 (SETQ I 0)
 (WHILE (< I (LENGTH KM_STONE_LIST))
 (SETQ ATTR_LIST (GET_ATTRIBUTES (NTH 0 (NTH I KM_STONE_LIST))))
 (SETQ KM (NTH 1 (ASSOC "KM" ATTR_LIST)))
 (SETQ KM_POINT_LIST (CONS (LIST (SUBSTR KM (+ (VL-STRING-POSITION (ASCII ":") KM) 2)) (NTH 1 (NTH I KM_STONE_LIST))) KM_POINT_LIST))
 (REVERSE KM_POINT_LIST)
 (SETQ I (+ I 1))
 )
 (REVERSE KM_POINT_LIST)
)


(DEFUN INSERT_OBSTRUCTIONS ( OBSTRUCTION_LIST KM_STONE_COORDINATES UP_OFFSET TR_OFFSET1 TR_OFFSET2 DN_OFFSET / I X-COORDINATE Y-COORDINATE BRNO )
  (SETQ I 0)
  (WHILE (< I (LENGTH OBSTRUCTION_LIST))
    (IF (/= (ASSOC (ITOA (FIX (NTH 0 (NTH I OBSTRUCTION_LIST)))) KM_STONE_COORDINATES) NIL)
    (PROGN
    (SETQ X-COORDINATE (+ (NTH 0 (NTH 1 (ASSOC (ITOA (FIX (NTH 0 (NTH I OBSTRUCTION_LIST)))) KM_STONE_COORDINATES))) (NTH 1 (NTH I OBSTRUCTION_LIST))))
    (IF (= (NTH 3 (NTH I OBSTRUCTION_LIST)) "UP") (SETQ Y-COORDINATE (NTH 1 UP_OFFSET)) (SETQ Y-COORDINATE (NTH 1 DN_OFFSET)))
    
    (IF (/= (VL-POSITION (NTH 2 (NTH I OBSTRUCTION_LIST)) (LIST "ROB" "RUB" "RFO" "BRIDGE" "MINOR BRIDGE" "MAJOR BRIDGE")) NIL)
    (PROGN
    (COMMAND "INSERT" "BRIDGE_2" (LIST X-COORDINATE (/ (+ (NTH 1 TR_OFFSET1) (NTH 1 TR_OFFSET2) ) 2) 0.0)   "1" "0" )
    (INSERT_DYNAMIC_PROPERTIES (ENTLAST) (LIST "WIDTH" "ADJ" "KM" "CHAINAGE" "TYPE") (LIST (NTH 4 (NTH I OBSTRUCTION_LIST)) (+ (- (/ (+ (NTH 1 TR_OFFSET1) (NTH 1 TR_OFFSET2) ) 2) (NTH 1 DN_OFFSET)) 20.00) (NTH 0 (NTH I OBSTRUCTION_LIST)) (NTH 1 (NTH I OBSTRUCTION_LIST)) (NTH 2 (NTH I OBSTRUCTION_LIST))))
    (IF (/= (NTH 5 (NTH I OBSTRUCTION_LIST)) NIL)
    (PROGN
    (IF (/= (TYPE (NTH 5 (NTH I OBSTRUCTION_LIST))) 'STR) (SETQ BRNO (RTOS (NTH 5 (NTH I OBSTRUCTION_LIST)) 2 0)) (SETQ BRNO (NTH 5 (NTH I OBSTRUCTION_LIST))))
    (MODIFY_ATTRIBUTES (ENTLAST) (LIST "BRIDGE_NO.") (LIST (STRCAT (NTH 2 (NTH I OBSTRUCTION_LIST)) " NO.:" BRNO)))
    )
    (PROGN
    (INSERT_DYNAMIC_PROPERTIES (ENTLAST) (LIST "BRV1") (LIST "WITHOUT BRIDGE NUMBER"))
    )
    )
    )
    )

    (IF (/= (VL-POSITION (NTH 2 (NTH I OBSTRUCTION_LIST)) (LIST "FOB" "SUB WAY")) NIL)
    (PROGN
    (COMMAND "INSERT" "FOB_SUBWAY" (LIST X-COORDINATE (/ (+ (NTH 1 TR_OFFSET1) (NTH 1 TR_OFFSET2) ) 2) 0.0)   "1" "0" )
    (INSERT_DYNAMIC_PROPERTIES (ENTLAST) (LIST "WIDTH" "ADJ" "KM" "CHAINAGE" "TYPE") (LIST (NTH 4 (NTH I OBSTRUCTION_LIST)) (+ (- (/ (+ (NTH 1 TR_OFFSET1) (NTH 1 TR_OFFSET2) ) 2) (NTH 1 DN_OFFSET)) 20.00) (NTH 0 (NTH I OBSTRUCTION_LIST)) (NTH 1 (NTH I OBSTRUCTION_LIST)) (NTH 2 (NTH I OBSTRUCTION_LIST))))
    (IF (/= (NTH 5 (NTH I OBSTRUCTION_LIST)) NIL)
    (PROGN
    (IF (/= (TYPE (NTH 5 (NTH I OBSTRUCTION_LIST))) 'STR) (SETQ BRNO (RTOS (NTH 5 (NTH I OBSTRUCTION_LIST)) 2 0)) (SETQ BRNO (NTH 5 (NTH I OBSTRUCTION_LIST))))
    (MODIFY_ATTRIBUTES (ENTLAST) (LIST "BRIDGE_NO.") (LIST (STRCAT (NTH 2 (NTH I OBSTRUCTION_LIST)) " NO.:" BRNO)))
    )
    (PROGN
    (INSERT_DYNAMIC_PROPERTIES (ENTLAST) (LIST "BRV1") (LIST "WITHOUT BRIDGE NUMBER"))
    )
    )
    ))

    (IF (/= (VL-POSITION (NTH 2 (NTH I OBSTRUCTION_LIST)) (LIST "POWER LINE CROSSING")) NIL)
    (PROGN
    (COMMAND "INSERT" "POWER_LINE-X-ING" (LIST X-COORDINATE (/ (+ (NTH 1 TR_OFFSET1) (NTH 1 TR_OFFSET2) ) 2) 0.0)   "1" "0" )
    )
    )

    (IF (/= (VL-POSITION (NTH 2 (NTH I OBSTRUCTION_LIST)) (LIST "SIGNAL DN")) NIL)
    (PROGN
    (COMMAND "INSERT" "SIGNAL_NEW" (LIST X-COORDINATE (NTH 1 TR_OFFSET1) 0.0)   "1" "0" )
    (INSERT_DYNAMIC_PROPERTIES (ENTLAST) (LIST "A1" "D2") (LIST (/ PI 2) 5.75))
    ))

    (IF (/= (VL-POSITION (NTH 2 (NTH I OBSTRUCTION_LIST)) (LIST "SIGNAL UP")) NIL)
    (PROGN
    (COMMAND "INSERT" "SIGNAL_NEW" (LIST X-COORDINATE (NTH 1 TR_OFFSET2) 0.0)   "1" "0" )
    (INSERT_DYNAMIC_PROPERTIES (ENTLAST) (LIST "A1" "D2") (LIST (* 3 (/ PI 2)) 5.75))
    ))
    
    (IF (/= (VL-POSITION (NTH 2 (NTH I OBSTRUCTION_LIST)) (LIST "CURVE START" "CURVE END" "TS" "SC" "CS" "ST")) NIL)
    (PROGN
    (COMMAND "INSERT" "REPRESENTATION1" (LIST X-COORDINATE Y-COORDINATE 0.0)   "1" "0" )
    (MODIFY_ATTRIBUTES (ENTLAST) (LIST "TEXT1" "TEXT2") (LIST (STRCAT "CH:" (ITOA (FIX (NTH 0 (NTH I OBSTRUCTION_LIST)))) "/" (RTOS (NTH 1 (NTH I OBSTRUCTION_LIST)) 2 2)) (NTH 2 (NTH I OBSTRUCTION_LIST))))
    (COMMAND "INSERT" "CURVE_SYMBOL" (LIST X-COORDINATE (NTH 1 TR_OFFSET1) 0.0)   "1" "0" )
    (COMMAND "INSERT" "CURVE_SYMBOL" (LIST X-COORDINATE (NTH 1 TR_OFFSET2) 0.0)   "1" "0" )
    (IF (/= (VL-POSITION (NTH 2 (NTH I OBSTRUCTION_LIST)) (LIST "CURVE START" "TS")) NIL)
      (COMMAND "INSERT" "CURVE_DETAILS" (LIST (+ X-COORDINATE 20) Y-COORDINATE 0.0)   "1" "0" )
    )
    (IF (/= (NTH 4 (NTH I OBSTRUCTION_LIST)) NIL) (MODIFY_ATTRIBUTES (ENTLAST) (LIST "RADIUS") (LIST (NTH 4 (NTH I OBSTRUCTION_LIST)))))
    (IF (/= (NTH 5 (NTH I OBSTRUCTION_LIST)) NIL) (MODIFY_ATTRIBUTES (ENTLAST) (LIST "CURVE_NO.") (LIST (NTH 5 (NTH I OBSTRUCTION_LIST)))))
    )
    )
    
    (IF (= (VL-POSITION (NTH 2 (NTH I OBSTRUCTION_LIST)) (LIST "ROB" "RUB" "BRIDGE" "MINOR BRIDGE" "MAJOR BRIDGE" "FOB" "SUB WAY" "CURVE STARTS" "CURVE ENDS" "TS" "SC" "CS" "ST")) NIL)
    (PROGN
    (COMMAND "INSERT" "REPRESENTATION1" (LIST X-COORDINATE Y-COORDINATE 0.0)   "1" "0" )
    (MODIFY_ATTRIBUTES (ENTLAST) (LIST "TEXT1" "TEXT2") (LIST (STRCAT "CH:" (ITOA (FIX (NTH 0 (NTH I OBSTRUCTION_LIST)))) "/" (RTOS (NTH 1 (NTH I OBSTRUCTION_LIST)) 2 2)) (NTH 2 (NTH I OBSTRUCTION_LIST))))
    ))
    
    )
    )
    
    (SETQ I (+ I 1))
  )
)


(DEFUN C:LOAD_OBSTRUCTION_FILE ( / )
  (OPENEXCEL (FINDFILE (GETFILED "SELECT OBSTRUCTION FILE" "" "" 8)) "Sheet1" T)
)







(DEFUN GET_MAST_INSERTION_POINTS_NORMAL ( OFFSET_ENTITIES1 TRACK_ENTITY SCALE / OFFSET_ENTITIES TRACK_ENTITY I TEMP_ELE1 TEMP_ELE2 LIST2 )
  (SETQ OFFSET_ENTITIES1 (FORM_SSSET OFFSET_ENTITIES1))
  (SETQ I 0)
  (SETQ OFFSET_ENTITIES NIL)
  (WHILE (< I (LENGTH OFFSET_ENTITIES1))
    (SETQ TEMP_ELE1 (CDR (ASSOC 10 (ENTGET (NTH I OFFSET_ENTITIES1)))))
    (SETQ OFFSET_ENTITIES (CONS (LIST (NTH I OFFSET_ENTITIES1) TEMP_ELE1) OFFSET_ENTITIES))
    (SETQ I (+ I 1))
  )
  (SETQ OFFSET_ENTITIES (REVERSE OFFSET_ENTITIES))
  (SETQ OFFSET_ENTITIES (SORT_FUN OFFSET_ENTITIES 1 0))
  
  (SETQ I 0)
  (SETQ TEMP_ELE1 NIL)
  (SETQ TEMP_ELE2 NIL)
  (SETQ LIST2 NIL)
  (WHILE (< I (LENGTH OFFSET_ENTITIES))
  (IF (/= (GEOM_INTERSECTWITH_MULTIPLE TRACK_ENTITY (NTH 0 (NTH I OFFSET_ENTITIES))) NIL)
    (PROGN
  (SETQ TEMP_ELE1 (NTH 0 (GEOM_INTERSECTWITH_MULTIPLE TRACK_ENTITY (NTH 0 (NTH I OFFSET_ENTITIES)))))
  (IF (/= (+ I 1) (LENGTH OFFSET_ENTITIES))
  (SETQ TEMP_ELE2 (ATOF  (RTOS (/ (ABS (- (CAR (NTH 1 (NTH (+ I 1) OFFSET_ENTITIES))) (CAR (NTH 1 (NTH I OFFSET_ENTITIES))))) SCALE) 2 1)))
  (SETQ TEMP_ELE2 NIL))
  (SETQ LIST2 (CONS (LIST  TEMP_ELE1 TEMP_ELE2 (NTH I OFFSET_ENTITIES)) LIST2))
     ))
  (SETQ I (+ I 1))
  )
  (SORT_FUN (REVERSE LIST2) 0 0)
)



(DEFUN GEOM_INTERSECTWITH_MULTIPLE ( TRACK_ENTITY_LIST OFFSET_ENTITY / I TEMP_ELE)
  (SETQ I 0)
  (SETQ TEMP_ELE NIL)
  (WHILE (< I (LENGTH TRACK_ENTITY_LIST))
     (SETQ TEMP_ELE (ACET-GEOM-INTERSECTWITH (NTH I TRACK_ENTITY) OFFSET_ENTITY 0.1))
     (IF (/= TEMP_ELE NIL) (PROGN (SETQ INTERSECTION_POINT TEMP_ELE) (SETQ I (LENGTH TRACK_ENTITY_LIST))))
     (SETQ I (+ I 1))
  )
TEMP_ELE
)






(DEFUN UPDATE_CHAINAGES_NORMAL (SCALE LOC_NO ST_CH ENT_LIST REFERENCE_TRACK / SSSET LOC_NO ST_CH ENT_LIST BS_PT BS_PT1 ENT_INFO VALUES VALUES1 VALUES2 VALUES3 VALUES4 FDN_REFERENCE FDN_REFERENCE_X FDN_REFERENCE_Y RD_REFERENCE RD_REFERENCE_X RD_REFERENCE_Y TC_REFERENCE TC_REFERENCE_X TC_REFERENCE_Y SPAN_REFERENCE_X SPAN_REFERENCE_Y ENT_LIST_SPAN POINT POINT1 POINT2 POINT3 ENT_LIST_SPAN VISIBILITY_SPAN VISIBILITY_TC VISIBILITY_FDN VISIBILITY_RD I LOC CH TEMP_ELE SCALE POINT_FDN POINT_RD POINT_TC TEMP_SPAN)
  ;(PROMPT "\n SELECT MASTS")
  ;(SETQ SSSET (SSGET))
  ;(SETQ SCALE (GETREAL "\n ENTER SCALE : "))
  ;(SETQ LOC_NO (GETSTRING "\n ENTER STARTING MAST LOCATION NUMBER :"))
  ;(SETQ ST_CH (GETSTRING "\n ENTER STARTING MAST CHAINAGE :"))
  (SETQ	KM_NO (SUBSTR LOC_NO 1 (VL-STRING-POSITION (ASCII "/") LOC_NO)))
  (SETQ	LOC_NO	(SUBSTR	LOC_NO (+ (VL-STRING-POSITION (ASCII "/") LOC_NO) 2)))
  (SETQ	ST_CH	(SUBSTR	ST_CH (+ (VL-STRING-POSITION (ASCII "/") ST_CH) 2)))
  
  ;(SETQ ENT_LIST (SINGLE_ELE_LIST (FILTER_LIST (LIST "SINGLE_CANT_MAST" "DOUBLE_CANT_MAST" "TRIPLE_CANT_MAST") (EXTRACT_ENTITY_INFO2 (FORM_SSSET SSSET)) 1) 0))
  (SETQ ENT_LIST (EXTRACT_ENTITY_INFO ENT_LIST 1 3))
  (SETQ ENT_LIST (SORT_FUN ENT_LIST 1 0))
  (SETQ ENT_LIST (SINGLE_ELE_LIST ENT_LIST 0))
  (SETQ BS_PT (CDR (ASSOC 10 (ENTGET (NTH 0 ENT_LIST)))))
  (SETQ BS_PT1 (CDR (ASSOC 10 (ENTGET REFERENCE_TRACK))))
  (SETQ ENT_INFO (YARD_STRUCTURE_INFO (NTH 0 ENT_LIST)))
  (SETQ VALUES (GET_DYNAMIC_PROPERTIES REFERENCE_TRACK (LIST "LOM1 X" "LOM1 Y")))
  (SETQ VALUES1 (GET_DYNAMIC_PROPERTIES REFERENCE_TRACK (LIST "LNM1 X" "LNM1 Y")))
  (SETQ VALUES2 (GET_DYNAMIC_PROPERTIES REFERENCE_TRACK (LIST "LCM1 X" "LCM1 Y")))
  (SETQ VALUES3 (GET_DYNAMIC_PROPERTIES REFERENCE_TRACK (LIST "LTM1 X" "LTM1 Y")))
  ;(SETQ FDN_REFERENCE (NTH 1 (NTH 0 (GET_TEXT_ALIGNMENT_POINT (LIST (NTH 0 ENT_LIST)) "FOUNDATION_TYPE1" 0))))
  ;(SETQ RD_REFERENCE (NTH 1 (NTH 0 (GET_TEXT_ALIGNMENT_POINT (LIST (NTH 0 ENT_LIST)) "RD1" 0))))
  (SETQ POINT (LIST (+ (CAR BS_PT) (CADR (ASSOC "LOM1 X" VALUES))) (+ (CADR BS_PT1) (CADR (ASSOC "LOM1 Y" VALUES))) 0.0))
  (SETQ POINT1 (LIST (+ (CAR BS_PT) (CADR (ASSOC "LNM1 X" VALUES1))) (+ (CADR BS_PT1) (CADR (ASSOC "LNM1 Y" VALUES1))) 0.0))
  (SETQ POINT2 (LIST (+ (CAR BS_PT) (CADR (ASSOC "LCM1 X" VALUES2))) (+ (CADR BS_PT1) (CADR (ASSOC "LCM1 Y" VALUES2))) 0.0))
  (SETQ POINT3 (LIST (+ (CAR BS_PT) (CADR (ASSOC "LTM1 X" VALUES3))) (+ (CADR BS_PT1) (CADR (ASSOC "LTM1 Y" VALUES3))) 0.0))
  (SETQ ENT_LIST_SPAN (ATTRIBUTES_FROM_ENTITIES ENT_LIST "SPAN1" 0))
  (SETQ I 0)
   (setq dcl_id (load_dialog "DISPLAY_INFO.dcl"))
   (new_dialog "DISPLAY_INFO" dcl_id)
  (WHILE (< I (LENGTH ENT_LIST_SPAN))
    (SETQ LOC (STRCAT KM_NO "/" LOC_NO))
    (SETQ CH (STRCAT KM_NO "/" ST_CH))
     (SET_TILE "INFO" (STRCAT "UPDATING LOC NO "  LOC " " "OF "  (ITOA (LENGTH ENT_LIST_SPAN))))
     (SET_TILE "PERCENTAGE" (STRCAT "UPDATING CHAINAGE " CH))
    (IF (= I (- (LENGTH ENT_LIST_SPAN) 1))
      (PROGN
      (SET_TILE "INFO" (STRCAT "ALL "  KM_NO "TH KILOMETER" " LOCATIONS ARE UPDATED SUCESSFULLY"))
      (SET_TILE "PERCENTAGE" "PRESS OK TO CONTINUE")
      )
    )
    
    (SETQ TEMP_ELE  (NTH I ENT_LIST_SPAN))
    (SETQ BASE_POINT (CDR (ASSOC 10 (ENTGET (NTH 0 TEMP_ELE)))))
    (MODIFY_ATTRIBUTES (NTH 0 TEMP_ELE) (LIST "MAST_NUMBER1" "CHAINAGE1") (LIST LOC CH))
    (INSERT_ATTRIBUTES1 (NTH 0 TEMP_ELE) (LIST "LOM1") (LIST POINT))
    (INSERT_ATTRIBUTES1 (NTH 0 TEMP_ELE) (LIST "LNM1") (LIST POINT1))
    (INSERT_ATTRIBUTES1 (NTH 0 TEMP_ELE) (LIST "LCM1") (LIST POINT2))
    (INSERT_ATTRIBUTES1 (NTH 0 TEMP_ELE) (LIST "LTM1") (LIST POINT3))
    ;(IF (/= I 0)
    ;(PROGN (CHANGE_TEXT_ALIGNMENT_POINT (NTH I ENT_LIST) '("FOUNDATION_TYPE1") (LIST FDN_REFERENCE))
    ;(CHANGE_TEXT_ALIGNMENT_POINT (NTH I ENT_LIST) '("RD1") (LIST RD_REFERENCE))
    ;)
    ;)
    (SETQ TEMP_SPAN (* (ATOF (NTH 1 TEMP_ELE)) SCALE))
    (IF (/= TEMP_SPAN 0)
    (PROGN
    (SETQ POINT (LIST (+ (CAR POINT) TEMP_SPAN) (CADR POINT) 0.0))
    (SETQ POINT1 (LIST (+ (CAR POINT1) TEMP_SPAN) (CADR POINT1) 0.0))
    (SETQ POINT2 (LIST (+ (CAR POINT2) TEMP_SPAN) (CADR POINT2) 0.0))
    (SETQ POINT3 (LIST (+ (CAR POINT3) TEMP_SPAN) (CADR POINT3) 0.0))
    ;(SETQ FDN_REFERENCE (LIST (+ (CAR FDN_REFERENCE) TEMP_SPAN)  (CADR FDN_REFERENCE)  0.0))
    ;(SETQ RD_REFERENCE  (LIST (+ (CAR RD_REFERENCE) TEMP_SPAN)  (CADR RD_REFERENCE)  0.0))
    )
    (PROGN
      (IF (/= I (- (LENGTH ENT_LIST_SPAN) 1)) (PROGN (SET_TILE "INFO" (STRCAT "SPAN HAS NOT BEEN ENTERED IN LOC NO "  LOC   ))
     (SET_TILE "PERCENTAGE" (STRCAT "PROGRAM STOPPED AT CHAINAGE " CH " PLEASE CHECK..."))))
      (SETQ I (LENGTH ENT_LIST_SPAN))
    ))
    (SETQ LOC_NO (ITOA (+ (ATOI LOC_NO) 2)))
    (SETQ ST_CH (RTOS (+ (ATOF ST_CH) (ATOF (NTH 1 TEMP_ELE))) 2 2))
    (SETQ I (+ I 1))
    )(setq ddiag(start_dialog))
)




(DEFUN FIND_IN_BETWEEN (LIST1 LIST2 A B C / I FINAL_LIST TEMP_ELE1 TEMP_ELE2 J TEMP_LIST TEMP_ELE3)
  (SETQ I 1 FINAL_LIST NIL)
  (WHILE (< I (LENGTH LIST1))
    (SETQ TEMP_ELE1 (NTH A (NTH (- I 1) LIST1)) TEMP_ELE2 (NTH A (NTH I LIST1)))
    (SETQ J 0 TEMP_LIST NIL)
    (WHILE (< J (LENGTH LIST2))
      (SETQ TEMP_ELE3 (NTH B (NTH C (NTH J LIST2))))
      (IF (AND (> TEMP_ELE3 TEMP_ELE1) (< TEMP_ELE3 TEMP_ELE2)) (SETQ TEMP_LIST (CONS (NTH J LIST2) TEMP_LIST)))
      (SETQ J (+ J 1))
    )
    (SETQ FINAL_LIST (CONS TEMP_LIST FINAL_LIST))
    (SETQ I (+ I 1))
  )
  (REVERSE FINAL_LIST)
)


(DEFUN UPDATE_TOTAL_CHAINAGES (LIST11 LIST22 SCALE STARTING_LOCATION REFERENCE_TRACK / I LOC_NO ST_CH ENT_LIST )
     (SETQ F 0 TEMP_ELE1 NIL TEMP_ELE2 NIL )
  (WHILE (< F (LENGTH LIST11))
    (SETQ TEMP_ELE1 (NTH F LIST11) TEMP_ELE2 (NTH F LIST22))
    (SETQ LOC_NO (STRCAT (NTH 0 TEMP_ELE1) "/" STARTING_LOCATION))
    (SETQ ST_CH (STRCAT (NTH 0 TEMP_ELE1) "/" (RTOS (- (NTH 0 (NTH 1 (NTH 0 (SORT_FUN TEMP_ELE2 1 0)))) (NTH 0 (NTH 1 TEMP_ELE1))) 2 2)))
    (SETQ ENT_LIST (SINGLE_ELE_LIST (SORT_FUN TEMP_ELE2 1 0) 0))
    (UPDATE_CHAINAGES_NORMAL SCALE LOC_NO ST_CH ENT_LIST REFERENCE_TRACK)
    (SETQ F (+ F 1))
  )
)



(DEFUN C:UPDATE_TOTAL_CHAINAGES ( / )
  (SETQ WPT1 (GETPOINT "ENTER STARTING POINT IN LOP"))
  (SETQ WPT2 (GETPOINT "\n ENTER ENDING POINT IN LOP"))
  (SETQ BLOCKS_LIST (FORM_SSSET (SSGET "W" WPT1 WPT2 (LIST (CONS 0 "INSERT")))))
  (SETQ MAST_ENTITIES (YARD_DATA_COLLECT WPT1 WPT2 '("SINGLE_CANT_MAST" "DOUBLE_CANT_MAST" "TRIPLE_CANT_MAST" "TTC" "SS1" "SS2" "SS3" "SS4") 1 5))
  (SETQ BLOCK_NAME_LIST (EXTRACT_ENTITY_INFO2 BLOCKS_LIST))
  (SETQ KM_STONE_LIST (FILTER_LIST (LIST "KM_NEW" "KM_STONE" "KMNEW" "KMSTONE") BLOCK_NAME_LIST 1))
  (SETQ KM_STONE_LIST (SORT_FUN (ENTITY_DFX (SINGLE_ELE_LIST KM_STONE_LIST 0) 10 -1) 1 0))
  (SETQ KM_STONE_COORDINATES (GET_KM_STONE_COORDINATES KM_STONE_LIST))
  (SETQ SCALE (GETREAL "\nENTER SCALE : "))
  ;(PROMPT "SELECT OFFSETS (OFFSET COLOUR CODE : GREEN->SINGLE CANTILEVER YELLOW->DOUBLE CANTILEVER")
  ;(SETQ OFFSET_ENTITIES1 (SSGET))
  ;(SETQ TRACK_ENTITY_UPTRACK (CAR(ENTSEL "\nSELECT TRACK ALIGNMENT FOR UP TRACK:")))
  ;(SETQ TRACK_ENTITY_DNTRACK (CAR(ENTSEL "\nSELECT TRACK ALIGNMENT FOR DN TRACK:")))
  (SETQ ENTNAME_UPTRACK (CAR(ENTSEL "\nSELECT REFERENCE MAST FOR UP TRACK:")))
  (SETQ ENTNAME_DNTRACK (CAR(ENTSEL "\nSELECT REFERENCE MAST FOR DN TRACK:")))
  (SETQ UPLINE_MAST_ENTITIES (FILTER_LIST '("DN") MAST_ENTITIES 1))
  (SETQ DNLINE_MAST_ENTITIES (FILTER_LIST '("UP") MAST_ENTITIES 1))
  (SETQ UPLINE_MAST_ENTITIES (EXTRACT_ENTITY_INFO (SINGLE_ELE_LIST UPLINE_MAST_ENTITIES 0) 1 3))
  (SETQ DNLINE_MAST_ENTITIES (EXTRACT_ENTITY_INFO (SINGLE_ELE_LIST DNLINE_MAST_ENTITIES 0) 1 3))
  (SETQ UPLINE_MASTS (FIND_IN_BETWEEN (SINGLE_ELE_LIST KM_STONE_COORDINATES 1) UPLINE_MAST_ENTITIES 0 0 1))
  (SETQ DNLINE_MASTS (FIND_IN_BETWEEN (SINGLE_ELE_LIST KM_STONE_COORDINATES 1) DNLINE_MAST_ENTITIES 0 0 1))
  (UPDATE_TOTAL_CHAINAGES (VL-REMOVE (NTH (- (LENGTH KM_STONE_COORDINATES) 1) KM_STONE_COORDINATES) KM_STONE_COORDINATES) UPLINE_MASTS SCALE "02" ENTNAME_UPTRACK)
  (UPDATE_TOTAL_CHAINAGES (VL-REMOVE (NTH (- (LENGTH KM_STONE_COORDINATES) 1) KM_STONE_COORDINATES) KM_STONE_COORDINATES) DNLINE_MASTS SCALE "01" ENTNAME_DNTRACK)
)







(DEFUN DATA_TO_STRUCTURE_MAP_SECTIONING (LIST1 LIST2 K Q  / I TEMP_ELE TEMP_ELE1 LIST3)
(SETQ I 0)
(SETQ TEMP_ELE NIL)
(SETQ TEMP_ELE1 NIL)
(SETQ LIST3 NIL)
(WHILE (< I (LENGTH LIST1))
  (SETQ TEMP_ELE1 (MAP_NEAREST1 LIST2 (NTH K (NTH I LIST1)) Q ))
  (SETQ TEMP_ELE (APPEND (LIST (NTH 0 (NTH I LIST1))) TEMP_ELE1 ))
  (SETQ LIST3 (CONS TEMP_ELE LIST3))
  ;(SETQ LIST2 (VL-REMOVE TEMP_ELE1 LIST2))
  (SETQ I (+ I 1))
  )
LIST3
)




(DEFUN C:GET_SECTIONING ( / WPT1 WPT2 POINT SCALE BLOCKS_LIST BLOCK_NAME_LIST KM_STONE_LIST ACC_LIST OLC_LIST KM_STONE_LIST ACC_LIST OLC_LIST MAST_TTC ANCHOR_LIST POINT_LIST ANCHOR_LIST ANCHOR_STRUCTURE_MAP_DATA ACC_STRUCTURE_MAP_DATA OLC_STRUCTURE_MAP_DATA)
  (SETQ WPT1 (GETPOINT "ENTER STARTING POINT IN LOP"))
  (SETQ WPT2 (GETPOINT "\n ENTER ENDING POINT IN LOP"))
  (SETQ BLOCKS_LIST (FORM_SSSET (SSGET "W" WPT1 WPT2 (LIST (CONS 0 "INSERT")))))
  (SETQ POINT (GETPOINT "\n ENTER INSERTION POINT"))
  (SETQ SCALE (GETINT "\n ENTER SCALE"))
  
  (SETQ BLOCK_NAME_LIST (EXTRACT_ENTITY_INFO2 BLOCKS_LIST))

  
  (SETQ KM_STONE_LIST (FILTER_LIST (LIST "KM_NEW" "KM_STONE" "KMNEW" "KMSTONE") BLOCK_NAME_LIST 1))
  
  (SETQ ACC_LIST (FILTER_LIST (LIST "ACC") BLOCK_NAME_LIST 1))
  (SETQ OLC_LIST (FILTER_LIST (LIST "OLC") BLOCK_NAME_LIST 1))
  (SETQ KM_STONE_LIST (SINGLE_ELE_LIST (SORT_FUN (ENTITY_DFX (SINGLE_ELE_LIST KM_STONE_LIST 0) 10 -1) 1 0) 0))
  (SETQ ACC_LIST (BUILD_LIST (ENTITY_DFX (SINGLE_ELE_LIST ACC_LIST 0) 10 -1) (LIST 0 1)))
  (SETQ OLC_LIST (BUILD_LIST (ENTITY_DFX (SINGLE_ELE_LIST OLC_LIST 0) 10 -1) (LIST 0 1)))
  (COMMAND "INSERT" "SECTIONING_FORMAT" POINT "1" "0" )
  (INSERT_DYNAMIC_PROPERTIES (ENTLAST) (LIST "FORMAT_LENGTH" "UP_LEFT_FLIP" "DN_RIGHT_FLIP")  (LIST (+ (* (- (LENGTH KM_STONE_LIST) 1) (/ 1000 SCALE)) 185.9044) 1 1))
  ;(COMMAND "BURST" (ENTLAST))
  (SETQ MAST_TTC (YARD_DATA_COLLECT WPT1 WPT2 '("SINGLE_CANT_MAST" "DOUBLE_CANT_MAST" "TRIPLE_CANT_MAST" "TTC" "SS0" "SS1" "SS2" "SS3" "SS4") 1 3)) 
  (SETQ ANCHOR_LIST (YARD_DATA_COLLECT WPT1 WPT2 '("ANCHOR" "BTB_ANC") 1 3))
  (IF (/= ANCHOR_LIST NIL) (SETQ ANCHOR_STRUCTURE_MAP_DATA (DATA_TO_STRUCTURE_MAP_SECTIONING ANCHOR_LIST MAST_TTC 1 1)) (SETQ ANCHOR_STRUCTURE_MAP_DATA NIL))
  (IF (/= ACC_LIST NIL) (SETQ ACC_STRUCTURE_MAP_DATA (DATA_TO_STRUCTURE_MAP1 ACC_LIST MAST_TTC 1 1)) (SETQ ACC_STRUCTURE_MAP_DATA NIL))
  (IF (/= OLC_LIST NIL) (SETQ OLC_STRUCTURE_MAP_DATA (DATA_TO_STRUCTURE_MAP1 OLC_LIST MAST_TTC 1 1)) (SETQ OLC_STRUCTURE_MAP_DATA NIL))
  (SETQ POINT (LIST (+ (CAR POINT) 92.9522) (+ (CADR POINT) 124.9774) 0.0))
  (SETQ POINT_LIST (KM_NOTATION_SECTIONING KM_STONE_LIST POINT SCALE))
  (IF (/= ANCHOR_LIST NIL) (ANCHOR_NOTATION_SECTIONING (INCLUDE_KM_NUMBER ANCHOR_STRUCTURE_MAP_DATA) POINT_LIST POINT SCALE))
  (IF (/= ACC_LIST NIL) (ACC_NOTATION_SECTIONING (INCLUDE_KM_NUMBER ACC_STRUCTURE_MAP_DATA) POINT_LIST SCALE))
  (IF (/= OLC_LIST NIL) (OLC_NOTATION_SECTIONING (INCLUDE_KM_NUMBER OLC_STRUCTURE_MAP_DATA) POINT_LIST POINT SCALE))
)

(DEFUN ENTITY_DFX (ENTITY_LIST DFX1 DFX2 / I FINAL_LIST DXF_LIST)
  (SETQ I 0)
  (SETQ FINAL_LIST NIL DXF_LIST NIL)
  (WHILE (< I (LENGTH ENTITY_LIST))
    (SETQ DXF_LIST (ENTGET (NTH I ENTITY_LIST)))
    (SETQ FINAL_LIST (CONS (LIST (NTH I ENTITY_LIST) (CDR (ASSOC DFX1 DXF_LIST)) (CDR (ASSOC DFX2 DXF_LIST))) FINAL_LIST))
    (SETQ I (+ I 1))
  )
(REVERSE FINAL_LIST)
)


(DEFUN INCLUDE_KM_NUMBER (STRUCTURE_MAP_DATA_LIST / I FINAL_LIST LOC_NO KM)
   (SETQ I 0)
   (SETQ FINAL_LIST NIL)
   (WHILE (< I (LENGTH STRUCTURE_MAP_DATA_LIST))
     (SETQ LOC_NO (NTH 1 (ASSOC "MAST_NUMBER1" (GET_ATTRIBUTES (NTH 1 (NTH I STRUCTURE_MAP_DATA_LIST))))))
     (SETQ KM (SUBSTR LOC_NO 1 (VL-STRING-POSITION (ASCII "/") LOC_NO)))
     (SETQ FINAL_LIST (CONS (LIST (NTH 0 (NTH I STRUCTURE_MAP_DATA_LIST)) (NTH 1 (NTH I STRUCTURE_MAP_DATA_LIST)) KM) FINAL_LIST))
     (SETQ I (+ I 1))
   )
  (REVERSE FINAL_LIST)
)


(DEFUN ANCHOR_NOTATION_SECTIONING (ANCHOR_STRUCTURE POINT_LIST POINT1 SCALE / I INS_PT INS_PT1 POINT ANCHOR EFF_NAME MAST MAST_CHAINAGE_DETAILS MAST_FLIP MAST_FLAG)
  (SETQ I 0)
  (SETQ INS_PT NIL POINT NIL ANCHOR NIL MAST NIL MAST_CHAINAGE_DETAILS NIL MAST_FLIP NIL)
  (WHILE (< I (LENGTH ANCHOR_STRUCTURE))
  (SETQ ANCHOR (NTH 0 (NTH I ANCHOR_STRUCTURE)) MAST (NTH 1 (NTH I ANCHOR_STRUCTURE)))
  (SETQ EFF_NAME (VLAX-GET-PROPERTY (VLAX-ENAME->VLA-OBJECT MAST) "EFFECTIVENAME"))
  (SETQ ANCHOR_ATTRIBUTES (NTH 1 (NTH 0 (FILTER_LIST (LIST "ANCHOR_TYPE1") (GET_ATTRIBUTES ANCHOR) 0))))
  (SETQ MAST_ATTRIBUTES (NTH 1 (NTH 0 (FILTER_LIST (LIST "CHAINAGE1") (GET_ATTRIBUTES MAST) 0))))
  (SETQ MAST_FLIP (NTH 1 (NTH 0 (GET_DYNAMIC_PROPERTIES MAST (LIST "STF1")))))
  (IF (/= (ASSOC (NTH 2 (NTH I ANCHOR_STRUCTURE)) POINT_LIST) NIL)
  (PROGN
  (SETQ POINT (NTH 1 (ASSOC (NTH 2 (NTH I ANCHOR_STRUCTURE)) POINT_LIST)))
  (IF (= EFF_NAME "SINGLE_CANT_MAST") (SETQ MAST_FLAG 0) (SETQ MAST_FLAG 1))
  (IF (= MAST_FLIP MAST_FLAG)
      (PROGN (SETQ INS_PT (LIST (+ (CAR POINT) (/ (ATOF (SUBSTR MAST_ATTRIBUTES (+ (VL-STRING-POSITION (ASCII "/") MAST_ATTRIBUTES) 2))) SCALE))  (- (CADR POINT) 26) 0.0))
	     
	     (IF (= ANCHOR_ATTRIBUTES "AEWA") (SETQ INS_PT1 (LIST (CAR INS_PT)  (+ (CADR POINT1) 22.7513) 0.0)))
	     (IF (= ANCHOR_ATTRIBUTES "FA") (SETQ INS_PT1 (LIST (CAR INS_PT)  (+ (CADR POINT1) 30.5025) 0.0)))
      )
      (PROGN
      (SETQ INS_PT (LIST (+ (CAR POINT) (/ (ATOF (SUBSTR MAST_ATTRIBUTES (+ (VL-STRING-POSITION (ASCII "/") MAST_ATTRIBUTES) 2))) SCALE))  (- (CADR POINT) 222) 0.0))
      
      (IF (= ANCHOR_ATTRIBUTES "AEWA") (SETQ INS_PT1 (LIST (CAR INS_PT)  (- (CADR POINT1) 22.7513) 0.0)))
      (IF (= ANCHOR_ATTRIBUTES "FA") (SETQ INS_PT1 (LIST (CAR INS_PT)  (- (CADR POINT1) 30.5025) 0.0)))
      )
  )
  (COMMAND "INSERT" "REPRESENTATION1" INS_PT "1" "0" )
  (MODIFY_ATTRIBUTES (ENTLAST) (LIST "TEXT1" "TEXT2") (LIST ANCHOR_ATTRIBUTES MAST_ATTRIBUTES))
  
  (IF (OR (= ANCHOR_ATTRIBUTES "FA") (= ANCHOR_ATTRIBUTES "AEWA"))
    (PROGN
    (COMMAND "INSERT" "BTB_SCH" INS_PT1 "1" "0" )
    (IF (/= MAST_FLIP MAST_FLAG) (INSERT_DYNAMIC_PROPERTIES (ENTLAST) (LIST "ACF1")  (LIST 1)))
    )
  )
  ))
  (SETQ I (+ I 1))
  )
)


(DEFUN KM_NOTATION_SECTIONING (KM_STONE_LIST POINT SCALE / I INS_PT ANCHOR MAST MAST_CHAINAGE_DETAILS MAST_FLIP KM_POINT_LIST)
  (SETQ POINT (LIST (CAR POINT) (+ (CADR POINT) 121.615) 0.0))
  (SETQ I 0)
  (SETQ INS_PT NIL ANCHOR NIL MAST NIL MAST_CHAINAGE_DETAILS NIL MAST_FLIP NIL)
  (WHILE (< I (LENGTH KM_STONE_LIST))
  (SETQ ATTR_LIST (GET_ATTRIBUTES (NTH I KM_STONE_LIST)))
  (IF (/= I (- (LENGTH KM_STONE_LIST) 1)) (SETQ LEFT_KM_NEXT (NTH 1 (ASSOC "LEFT_KM" (GET_ATTRIBUTES (NTH (+ I 1) KM_STONE_LIST))))))
  (SETQ KM (NTH 1 (ASSOC "KM" ATTR_LIST)) LEFT_KM (NTH 1 (ASSOC "LEFT_KM" ATTR_LIST)) RIGHT_KM (NTH 1 (ASSOC "RIGHT_KM" ATTR_LIST)))
  (COMMAND "INSERT" "KM_NEW" POINT "1" "0" )
  (SETQ KM_POINT_LIST (CONS (LIST (SUBSTR KM (+ (VL-STRING-POSITION (ASCII ":") KM) 2)) POINT) KM_POINT_LIST))
  (MODIFY_ATTRIBUTES (ENTLAST) (LIST "KM" "LEFT_KM" "RIGHT_KM") (LIST KM LEFT_KM RIGHT_KM))
  (SETQ POINT (LIST (+ (CAR POINT) (/ (ATOF (SUBSTR LEFT_KM_NEXT (+ (VL-STRING-POSITION (ASCII "/") LEFT_KM_NEXT) 2))) SCALE))  (CADR POINT) 0.0))
  (SETQ I (+ I 1))
  )
  (REVERSE KM_POINT_LIST)
)


(DEFUN ACC_NOTATION_SECTIONING (ACC_STRUCTURE POINT_LIST SCALE / I INS_PT INS_PT1 ACC ACC_ATTRIBUTES MAST_ATTRIBUTES MAST_FLIP ACC_FLIP POINT MAST_COUNT1_POINT MAST_COUNT2_POINT ANCHOR MAST MAST_CHAINAGE_DETAILS MAST_FLIP ACC_NATURE)
  (SETQ I 0)
  (SETQ INS_PT NIL ANCHOR NIL MAST NIL MAST_CHAINAGE_DETAILS NIL MAST_FLIP NIL)
  (WHILE (< I (LENGTH ACC_STRUCTURE))
  (SETQ ACC (NTH 0 (NTH I ACC_STRUCTURE)) MAST (NTH 1 (NTH I ACC_STRUCTURE)))
  (SETQ ACC_ATTRIBUTES (GET_ATTRIBUTES ACC))
  (SETQ MAST_ATTRIBUTES (NTH 1 (NTH 0 (FILTER_LIST (LIST "CHAINAGE1") (GET_ATTRIBUTES MAST) 0))))
  (SETQ MAST_FLIP (NTH 1 (NTH 0 (GET_DYNAMIC_PROPERTIES MAST (LIST "STF1")))))
  (SETQ ACC_FLIP (NTH 1 (NTH 0 (GET_DYNAMIC_PROPERTIES ACC (LIST "ACF1")))))
  (IF (/= (ASSOC (NTH 2 (NTH I ACC_STRUCTURE)) POINT_LIST) NIL)
  (PROGN
  (SETQ POINT (NTH 1 (ASSOC (NTH 2 (NTH I ACC_STRUCTURE)) POINT_LIST)))
  (IF (= MAST_FLIP 0)
      (PROGN
      (SETQ INS_PT1 (LIST (+ (CAR POINT) (/ (ATOF (SUBSTR MAST_ATTRIBUTES (+ (VL-STRING-POSITION (ASCII "/") MAST_ATTRIBUTES) 2))) SCALE))  (- (CADR POINT) 26) 0.0))
      (SETQ INS_PT (LIST (+ (CAR POINT) (/ (ATOF (SUBSTR MAST_ATTRIBUTES (+ (VL-STRING-POSITION (ASCII "/") MAST_ATTRIBUTES) 2))) SCALE))  (- (CADR POINT) 86.00) 0.0))
      )
      (PROGN
      (SETQ INS_PT1 (LIST (+ (CAR POINT) (/ (ATOF (SUBSTR MAST_ATTRIBUTES (+ (VL-STRING-POSITION (ASCII "/") MAST_ATTRIBUTES) 2))) SCALE))  (- (CADR POINT) 222) 0.0))
      (SETQ INS_PT (LIST (+ (CAR POINT) (/ (ATOF (SUBSTR MAST_ATTRIBUTES (+ (VL-STRING-POSITION (ASCII "/") MAST_ATTRIBUTES) 2))) SCALE))  (- (CADR POINT) 185.00) 0.0))
      )
  )
  (COMMAND "INSERT" "ACC" INS_PT "1" "0" )
  (MODIFY_ATTRIBUTES (ENTLAST) (SINGLE_ELE_LIST ACC_ATTRIBUTES 0)  (SINGLE_ELE_LIST ACC_ATTRIBUTES 1))
  (INSERT_DYNAMIC_PROPERTIES (ENTLAST) (LIST "ACF1")  (LIST ACC_FLIP))
  (SETQ MAST_COUNT1_POINT (NTH 2 (ASSOC "MAST_COUNT1" (GET_ATTRIBUTES (ENTLAST)))) MAST_COUNT2_POINT (NTH 2 (ASSOC "MAST_COUNT2" (GET_ATTRIBUTES (ENTLAST)))) ACC_NATURE (NTH 2 (ASSOC "ACC_NATURE" (GET_ATTRIBUTES (ENTLAST)))))
  (IF (= ACC_FLIP 1) (INSERT_ATTRIBUTES (ENTLAST) (LIST "MAST_COUNT1" "MAST_COUNT2")  (LIST (LIST (CAR MAST_COUNT1_POINT) (- (CADR MAST_COUNT1_POINT) 5.5) 0.0) (LIST (CAR MAST_COUNT2_POINT) (- (CADR MAST_COUNT2_POINT) 5.5) 0.0))))
  (INSERT_ATTRIBUTES (ENTLAST) (LIST "ACC_NATURE" )  (LIST (LIST (- (CAR ACC_NATURE) 2.5) (CADR ACC_NATURE) 0.0)))
  (COMMAND "INSERT" "REPRESENTATION1" INS_PT1 "1" "0" )
  (MODIFY_ATTRIBUTES (ENTLAST) (LIST "TEXT1" "TEXT2") (LIST "ACC" MAST_ATTRIBUTES))
  )
  )
  (SETQ I (+ I 1))
  )
)


(DEFUN OLC_NOTATION_SECTIONING (ACC_STRUCTURE POINT_LIST POINT1 SCALE / I INS_PT POINT ANCHOR MAST MAST_CHAINAGE_DETAILS MAST_FLIP)
  (SETQ I 0)
  (SETQ INS_PT NIL ANCHOR NIL MAST NIL MAST_CHAINAGE_DETAILS NIL MAST_FLIP NIL)
  (WHILE (< I (LENGTH ACC_STRUCTURE))
  (SETQ ACC (NTH 0 (NTH I ACC_STRUCTURE)) MAST (NTH 1 (NTH I ACC_STRUCTURE)))
  (SETQ ACC_ATTRIBUTES (GET_ATTRIBUTES ACC))
  (SETQ MAST_ATTRIBUTES (NTH 1 (NTH 0 (FILTER_LIST (LIST "CHAINAGE1") (GET_ATTRIBUTES MAST) 0))))
  (SETQ MAST_FLIP (NTH 1 (NTH 0 (GET_DYNAMIC_PROPERTIES MAST (LIST "STF1")))))
  (IF (/= (ASSOC (NTH 2 (NTH I ACC_STRUCTURE)) POINT_LIST) NIL)
  (PROGN
  (SETQ POINT (NTH 1 (ASSOC (NTH 2 (NTH I ACC_STRUCTURE)) POINT_LIST)))
  ;(SETQ ACC_FLIP (NTH 1 (NTH 0 (GET_DYNAMIC_PROPERTIES ACC (LIST "ACF1")))))
  ;(SETQ MAST_COUNT1_POINT (NTH 2 (ASSOC "MAST_COUNT1" ACC_ATTRIBUTES))
  (IF (= MAST_FLIP 1)
      (PROGN
      (SETQ INS_PT (LIST (+ (CAR POINT) (/ (ATOF (SUBSTR MAST_ATTRIBUTES (+ (VL-STRING-POSITION (ASCII "/") MAST_ATTRIBUTES) 2))) SCALE))  (- (CADR POINT) 45.00) 0.0))
      (SETQ INS_PT1 (LIST (CAR INS_PT)  (+ (CADR POINT1) 15) 0.0))
      )
      (PROGN
      (SETQ INS_PT (LIST (+ (CAR POINT) (/ (ATOF (SUBSTR MAST_ATTRIBUTES (+ (VL-STRING-POSITION (ASCII "/") MAST_ATTRIBUTES) 2))) SCALE))  (- (CADR POINT) 157.00) 0.0))
      (SETQ INS_PT1 (LIST (CAR INS_PT)  (- (CADR POINT1) 15) 0.0))
      )
  )
  (COMMAND "INSERT" "OLC" INS_PT "1" "0" )
  (MODIFY_ATTRIBUTES (ENTLAST) (SINGLE_ELE_LIST ACC_ATTRIBUTES 0)  (SINGLE_ELE_LIST ACC_ATTRIBUTES 1))
  (COMMAND "INSERT" "BWA_SCH" INS_PT1 "1" "0" )
  )
  )
  ;(INSERT_DYNAMIC_PROPERTIES (ENTLAST) (LIST "ACF1")  (LIST ACC_FLIP))
  ;(INSERT_ATTRIBUTES (ENTLAST) (LIST "MAST_COUNT1" "MAST_COUNT2")  (LIST ACC_FLIP))
  (SETQ I (+ I 1))
  )
)






(DEFUN INDENTIFY_LOCATIONS ( SNAP_POINTS TRACK_TYPE / I FINAL_LIST PREV_COLOUR_CODE NEXT_COLOUR_CODE LOC )
  (SETQ I 0)
  (SETQ FINAL_LIST NIL PREV_COLOUR_CODE NIL NEXT_COLOUR_CODE NIL)
  (WHILE (< I (LENGTH SNAP_POINTS))
    (SETQ COLOUR_CODE (CDR (ASSOC 62  (ENTGET (NTH 0 (NTH 2 (NTH I SNAP_POINTS)))))))
    (IF (/= I 0)
      (SETQ PREV_COLOUR_CODE (CDR (ASSOC 62  (ENTGET (NTH 0 (NTH 2 (NTH (- I 1) SNAP_POINTS)))))))
      (SETQ PREV_COLOUR_CODE NIL)
    )
    (IF (/= I (- (LENGTH SNAP_POINTS) 1))
      (SETQ NEXT_COLOUR_CODE (CDR (ASSOC 62  (ENTGET (NTH 0 (NTH 2 (NTH (+ I 1) SNAP_POINTS)))))))
      (SETQ NEXT_COLOUR_CODE NIL)
    )
    (SETQ LOC NIL)
  (IF (= COLOUR_CODE 3)
    (PROGN
    (IF (AND (/= (VL-POSITION PREV_COLOUR_CODE (LIST 2 5 1)) NIL) (/= NEXT_COLOUR_CODE 2))
      (SETQ LOC "BWA_END")
    )
    
    (IF (AND (/= PREV_COLOUR_CODE 2) (/= (VL-POSITION NEXT_COLOUR_CODE (LIST 2 5 1)) NIL))
      (SETQ LOC "BWA_START")
    )

    (IF (/= (VL-POSITION PREV_COLOUR_CODE (LIST 7 8 9)) NIL)
      (SETQ LOC "ACA_END")
    )
    
    (IF (/= (VL-POSITION NEXT_COLOUR_CODE (LIST 7 8 9)) NIL)
      (SETQ LOC "ACA_START")
    )
    
    (IF (AND (= PREV_COLOUR_CODE 3) (= NEXT_COLOUR_CODE 3))
      (SETQ LOC "NORMAL")
    )
    
    )
  )

  (IF (/= (VL-POSITION COLOUR_CODE (LIST 2 5 1)) NIL)
    (PROGN
    (IF (= COLOUR_CODE 2)
      (PROGN
    (IF (AND (/= (VL-POSITION PREV_COLOUR_CODE (LIST 2 5 1)) NIL) (/= (VL-POSITION NEXT_COLOUR_CODE (LIST 2 5 1)) NIL))
      (SETQ LOC "OLC")
      (SETQ LOC "DOUBLE")
    )
      )
    )
    (IF (/= (VL-POSITION COLOUR_CODE (LIST 5 1)) NIL)
      (PROGN
    (IF (AND (/= (VL-POSITION PREV_COLOUR_CODE (LIST 2 5 1)) NIL) (/= (VL-POSITION NEXT_COLOUR_CODE (LIST 2 5 1)) NIL))
      (PROGN
      (IF (= COLOUR_CODE 5)
      (SETQ LOC "OLCAEWA")
      (SETQ LOC "OLCFA")
      ))
      (PROGN
      (IF (= COLOUR_CODE 5)
      (SETQ LOC "DAEWA")
      (SETQ LOC "DFA")
      ))
    )
      )
    )
    )
  )

  (IF (= COLOUR_CODE 7)
  (SETQ LOC "ACC")
  )

  (IF (= COLOUR_CODE 4)
  (SETQ LOC "AEWA")
  )

  (IF (= COLOUR_CODE 6)
  (SETQ LOC "FA")
  )




  (IF (= COLOUR_CODE 8)
  (SETQ LOC "ACCFA")
  )

  (IF (= COLOUR_CODE 9)
  (SETQ LOC "ACCAEWA")
  )
    

 (SETQ FINAL_LIST (CONS LOC FINAL_LIST))
 (SETQ I (+ I 1))
 )
 
 (ADD_LISTS SNAP_POINTS (BUILD_LIST (WIRE_NUMBERING (REVERSE FINAL_LIST) TRACK_TYPE) (LIST 1 2 3)))
 )





(DEFUN INSERT_MASTS_NORMAL ( OFFSET_ENTITIES1 TRACK_ENTITY SCALE ENTNAME / SNAP_POINTS I TEMP_ELE INSERTION_POINT MAST_LENGTH VALUES POINT IMP_REFERENCE SG_REFERENCE FLAG MAST_LIST IMP_POINT STAG_POINT SCALE)

(SETQ SNAP_POINTS (GET_MAST_INSERTION_POINTS_NORMAL OFFSET_ENTITIES1 TRACK_ENTITY SCALE))
(SETQ SNAP_POINTS (INDENTIFY_LOCATIONS SNAP_POINTS "UP"))
(SETQ BS_PT (CDR (ASSOC 10 (ENTGET ENTNAME))))
(SETQ AS (GET_DYNAMIC_PROPERTIES ENTNAME '("STL1" "SGM1 X" "IMM1 X" "SGM1 Y" "IMM1 Y")))
(SETQ MAST_LENGTH (CADR(ASSOC "STL1" AS)))
(SETQ IMP_REFERENCE (LIST (CADR(ASSOC "IMM1 X" AS)) (CADR(ASSOC "IMM1 Y" AS)) 0.0))
(SETQ SG_REFERENCE (LIST (CADR(ASSOC "SGM1 X" AS)) (CADR(ASSOC "SGM1 Y" AS)) 0.0))
  (SETQ FDN_REFERENCE (GET_TEXT_ALIGNMENT_POINT (LIST ENTNAME) "FOUNDATION_TYPE1" 0))
  (SETQ FDN_REFERENCE_X (- (NTH 0 (NTH 1 (NTH 0 FDN_REFERENCE)))  (NTH 0 (CDR (ASSOC 10 (ENTGET ENTNAME))))))
  (SETQ FDN_REFERENCE_Y (- (NTH 1 (NTH 1 (NTH 0 FDN_REFERENCE)))  (NTH 1 (CDR (ASSOC 10 (ENTGET ENTNAME))))))
  (SETQ RD_REFERENCE (GET_TEXT_ALIGNMENT_POINT (LIST ENTNAME) "RD1" 0))
  (SETQ RD_REFERENCE_X (- (NTH 0 (NTH 1 (NTH 0 RD_REFERENCE)))  (NTH 0 (CDR (ASSOC 10 (ENTGET ENTNAME))))))
  (SETQ RD_REFERENCE_Y (- (NTH 1 (NTH 1 (NTH 0 RD_REFERENCE)))  (NTH 1 (CDR (ASSOC 10 (ENTGET ENTNAME))))))
  (SETQ TC_REFERENCE (GET_TEXT_ALIGNMENT_POINT (LIST ENTNAME) "TC1" 0))
  (SETQ TC_REFERENCE_X (- (NTH 0 (NTH 1 (NTH 0 TC_REFERENCE)))  (NTH 0 (CDR (ASSOC 10 (ENTGET ENTNAME))))))
  (SETQ TC_REFERENCE_Y (- (NTH 1 (NTH 1 (NTH 0 TC_REFERENCE)))  (NTH 1 (CDR (ASSOC 10 (ENTGET ENTNAME))))))
  (SETQ SPAN_REFERENCE (GET_TEXT_ALIGNMENT_POINT (LIST ENTNAME) "SPAN1" 0))
  (SETQ SPAN_REFERENCE_X (- (NTH 0 (NTH 1 (NTH 0 SPAN_REFERENCE)))  (NTH 0 (CDR (ASSOC 10 (ENTGET ENTNAME))))))
  (SETQ SPAN_REFERENCE_Y (- (NTH 1 (NTH 1 (NTH 0 SPAN_REFERENCE)))  (NTH 1 (CDR (ASSOC 10 (ENTGET ENTNAME))))))
  (SETQ VISIBILITY_FDN (NTH 0 (SINGLE_ELE_LIST (EXTRACT_ATTRIBUTES ENTNAME (LIST "FOUNDATION_TYPE1" ) 3) 1)))
  (SETQ VISIBILITY_RD (NTH 0 (SINGLE_ELE_LIST (EXTRACT_ATTRIBUTES ENTNAME (LIST "RD1" ) 3) 1)))
  (SETQ VISIBILITY_SPAN (NTH 0 (SINGLE_ELE_LIST (EXTRACT_ATTRIBUTES ENTNAME (LIST "SPAN1" ) 3) 1)))
  (SETQ VISIBILITY_TC (NTH 0 (SINGLE_ELE_LIST (EXTRACT_ATTRIBUTES ENTNAME (LIST "TC1" ) 3) 1)))
(SETQ FLAG "Y")
(SETQ MAST_LIST NIL)
(SETQ I 0)
(WHILE (< I (LENGTH SNAP_POINTS))
(SETQ TEMP_ELE (NTH 0 (NTH I SNAP_POINTS)))
(SETQ COLOUR_CODE (CDR (ASSOC 62  (ENTGET (NTH 0 (NTH 2 (NTH I SNAP_POINTS)))))))



(IF (/= (VL-POSITION COLOUR_CODE (LIST 3 8 9)) NIL)
(PROGN
(SETQ INSERTION_POINT (LIST (CAR TEMP_ELE) (+ (CADR TEMP_ELE) MAST_LENGTH) 0.0))
(COMMAND "INSERT" "SINGLE_CANT_MAST" INSERTION_POINT "1" "0" )
(SETQ MAST_LIST (CONS (LIST (ENTLAST) INSERTION_POINT) MAST_LIST))
(IF (/= I (- (LENGTH SNAP_POINTS) 1)) (PROGN (MODIFY_ATTRIBUTES (ENTLAST) '("SPAN1") (LIST (RTOS (NTH 1 (NTH I SNAP_POINTS)) 2 2)))
;(INSERT_ATTRIBUTES (ENTLAST) '("SPAN1") (LIST (LIST (+ (CAR INSERTION_POINT) (* (/ (NTH 1 (NTH I SNAP_POINTS)) 2) SCALE))  (+ (CADR INSERTION_POINT) SPAN_REFERENCE) 0.0)))
))

(SETQ IMP_POINT (ADDITION INSERTION_POINT IMP_REFERENCE))
(SETQ STAG_POINT (ADDITION INSERTION_POINT SG_REFERENCE))
(SETQ POINT1 (LIST  (CAR TEMP_ELE)  (+  (CADR TEMP_ELE) 175.00) 0.0))
(INSERT_ATTRIBUTES1 (ENTLAST) (LIST "IMM1") (LIST IMP_POINT))
(INSERT_ATTRIBUTES1 (ENTLAST) (LIST "SGM1") (LIST STAG_POINT))
(CHANGE_DYNAMIC_PROPERTIES (ENTLAST) '("STL1") (LIST MAST_LENGTH))
(INSERT_ATTRIBUTES1 (ENTLAST) (LIST "LOM1") (LIST POINT1))
(CHANGE_TEXT_ALIGNMENT_POINT (ENTLAST) '("FOUNDATION_TYPE1") (LIST (LIST (CAR INSERTION_POINT)  (+ (CADR BS_PT) FDN_REFERENCE_Y) 0.0)))
    (CHANGE_TEXT_ALIGNMENT_POINT (ENTLAST) '("RD1") (LIST (LIST (CAR INSERTION_POINT)  (+ (CADR BS_PT) RD_REFERENCE_Y) 0.0)))
    (CHANGE_TEXT_ALIGNMENT_POINT (ENTLAST) '("TC1") (LIST (LIST (+ (CAR INSERTION_POINT) TC_REFERENCE_X)  (+ (CADR INSERTION_POINT) TC_REFERENCE_Y) 0.0)))
    (CHANGE_VISIBILITY (ENTLAST) (LIST "FOUNDATION_TYPE1" "RD1" "SPAN1" "TC1" ) (LIST (ITOA VISIBILITY_FDN) (ITOA VISIBILITY_RD) (ITOA VISIBILITY_SPAN) (ITOA VISIBILITY_TC)))
(IF (/= (NTH 1 (NTH I SNAP_POINTS)) NIL) (CHANGE_TEXT_ALIGNMENT_POINT (ENTLAST) '("SPAN1") (LIST (LIST (IF (/= (NTH 1 (NTH I SNAP_POINTS)) 0) (+ (CAR INSERTION_POINT) (/ (* (NTH 1 (NTH I SNAP_POINTS)) SCALE) 2)) (+ (CAR INSERTION_POINT) SPAN_REFERENCE_X))  (+ (CADR INSERTION_POINT) SPAN_REFERENCE_Y) 0.0))))

(IF (= FLAG "Y")
(PROGN (COMMAND "INSERT" "SUPER_MAST" INSERTION_POINT "1" "0" )
(CHANGE_FLIP (ENTLAST) "STF1"))
)
(INSERT_ADDITIONAL_BLOCKS INSERTION_POINT (NTH I SNAP_POINTS) "UP")
))


  

(IF (= COLOUR_CODE 7)
(PROGN
(SETQ INSERTION_POINT (LIST (CAR TEMP_ELE) (+ (CADR TEMP_ELE) MAST_LENGTH) 0.0))
(COMMAND "INSERT" "SINGLE_CANT_MAST" INSERTION_POINT "1" "0" )
(SETQ MAST_LIST (CONS (LIST (ENTLAST) INSERTION_POINT) MAST_LIST))
(IF (/= I (- (LENGTH SNAP_POINTS) 1)) (PROGN (MODIFY_ATTRIBUTES (ENTLAST) '("SPAN1") (LIST (RTOS (NTH 1 (NTH I SNAP_POINTS)) 2 2)))
;(INSERT_ATTRIBUTES (ENTLAST) '("SPAN1") (LIST (LIST (+ (CAR INSERTION_POINT) (* (/ (NTH 1 (NTH I SNAP_POINTS)) 2) SCALE))  (+ (CADR INSERTION_POINT) SPAN_REFERENCE) 0.0)))
))

(SETQ IMP_POINT (ADDITION INSERTION_POINT IMP_REFERENCE))
(SETQ STAG_POINT (ADDITION INSERTION_POINT SG_REFERENCE))
(SETQ POINT1 (LIST  (CAR TEMP_ELE)  (+  (CADR TEMP_ELE) 175.00) 0.0))
(INSERT_ATTRIBUTES1 (ENTLAST) (LIST "IMM1") (LIST IMP_POINT))
(INSERT_ATTRIBUTES1 (ENTLAST) (LIST "SGM1") (LIST STAG_POINT))
(CHANGE_DYNAMIC_PROPERTIES (ENTLAST) '("STL1") (LIST MAST_LENGTH))
(INSERT_ATTRIBUTES1 (ENTLAST) (LIST "LOM1") (LIST POINT1))
(CHANGE_TEXT_ALIGNMENT_POINT (ENTLAST) '("FOUNDATION_TYPE1") (LIST (LIST (CAR INSERTION_POINT)  (+ (CADR BS_PT) FDN_REFERENCE_Y) 0.0)))
    (CHANGE_TEXT_ALIGNMENT_POINT (ENTLAST) '("RD1") (LIST (LIST (CAR INSERTION_POINT)  (+ (CADR BS_PT) RD_REFERENCE_Y) 0.0)))
    (CHANGE_TEXT_ALIGNMENT_POINT (ENTLAST) '("TC1") (LIST (LIST (+ (CAR INSERTION_POINT) TC_REFERENCE_X)  (+ (CADR INSERTION_POINT) TC_REFERENCE_Y) 0.0)))
    (CHANGE_VISIBILITY (ENTLAST) (LIST "FOUNDATION_TYPE1" "RD1" "SPAN1" "TC1" ) (LIST (ITOA VISIBILITY_FDN) (ITOA VISIBILITY_RD) (ITOA VISIBILITY_SPAN) (ITOA VISIBILITY_TC)))
(IF (/= (NTH 1 (NTH I SNAP_POINTS)) NIL) (CHANGE_TEXT_ALIGNMENT_POINT (ENTLAST) '("SPAN1") (LIST (LIST (IF (/= (NTH 1 (NTH I SNAP_POINTS)) 0) (+ (CAR INSERTION_POINT) (/ (* (NTH 1 (NTH I SNAP_POINTS)) SCALE) 2)) (+ (CAR INSERTION_POINT) SPAN_REFERENCE_X))  (+ (CADR INSERTION_POINT) SPAN_REFERENCE_Y) 0.0))))

(IF (= FLAG "Y")
(PROGN (COMMAND "INSERT" "SUPER_MAST" INSERTION_POINT "1" "0" )
(CHANGE_FLIP (ENTLAST) "STF1"))
)
(INSERT_ADDITIONAL_BLOCKS INSERTION_POINT (NTH I SNAP_POINTS) "UP")
))


(IF (= COLOUR_CODE 4)
(PROGN
(SETQ INSERTION_POINT (LIST (CAR TEMP_ELE) (+ (CADR TEMP_ELE) MAST_LENGTH) 0.0))
(COMMAND "INSERT" "SINGLE_CANT_MAST" INSERTION_POINT "1" "0" )
(SETQ MAST_LIST (CONS (LIST (ENTLAST) INSERTION_POINT) MAST_LIST))
(IF (/= I (- (LENGTH SNAP_POINTS) 1)) (PROGN (MODIFY_ATTRIBUTES (ENTLAST) '("SPAN1") (LIST (RTOS (NTH 1 (NTH I SNAP_POINTS)) 2 2)))
;(INSERT_ATTRIBUTES (ENTLAST) '("SPAN1") (LIST (LIST (+ (CAR INSERTION_POINT) (* (/ (NTH 1 (NTH I SNAP_POINTS)) 2) SCALE))  (+ (CADR INSERTION_POINT) SPAN_REFERENCE) 0.0)))
))

(SETQ IMP_POINT (ADDITION INSERTION_POINT IMP_REFERENCE))
(SETQ STAG_POINT (ADDITION INSERTION_POINT SG_REFERENCE))
(SETQ POINT1 (LIST  (CAR TEMP_ELE)  (+  (CADR TEMP_ELE) 175.00) 0.0))
(INSERT_ATTRIBUTES1 (ENTLAST) (LIST "IMM1") (LIST IMP_POINT))
(INSERT_ATTRIBUTES1 (ENTLAST) (LIST "SGM1") (LIST STAG_POINT))
(CHANGE_DYNAMIC_PROPERTIES (ENTLAST) '("STL1") (LIST MAST_LENGTH))
(INSERT_ATTRIBUTES1 (ENTLAST) (LIST "LOM1") (LIST POINT1))
(CHANGE_TEXT_ALIGNMENT_POINT (ENTLAST) '("FOUNDATION_TYPE1") (LIST (LIST (CAR INSERTION_POINT)  (+ (CADR BS_PT) FDN_REFERENCE_Y) 0.0)))
    (CHANGE_TEXT_ALIGNMENT_POINT (ENTLAST) '("RD1") (LIST (LIST (CAR INSERTION_POINT)  (+ (CADR BS_PT) RD_REFERENCE_Y) 0.0)))
    (CHANGE_TEXT_ALIGNMENT_POINT (ENTLAST) '("TC1") (LIST (LIST (+ (CAR INSERTION_POINT) TC_REFERENCE_X)  (+ (CADR INSERTION_POINT) TC_REFERENCE_Y) 0.0)))
    (CHANGE_VISIBILITY (ENTLAST) (LIST "FOUNDATION_TYPE1" "RD1" "SPAN1" "TC1" ) (LIST (ITOA VISIBILITY_FDN) (ITOA VISIBILITY_RD) (ITOA VISIBILITY_SPAN) (ITOA VISIBILITY_TC)))
(IF (/= (NTH 1 (NTH I SNAP_POINTS)) NIL) (CHANGE_TEXT_ALIGNMENT_POINT (ENTLAST) '("SPAN1") (LIST (LIST (IF (/= (NTH 1 (NTH I SNAP_POINTS)) 0) (+ (CAR INSERTION_POINT) (/ (* (NTH 1 (NTH I SNAP_POINTS)) SCALE) 2)) (+ (CAR INSERTION_POINT) SPAN_REFERENCE_X))  (+ (CADR INSERTION_POINT) SPAN_REFERENCE_Y) 0.0))))

(IF (= FLAG "Y")
(PROGN (COMMAND "INSERT" "SUPER_MAST" INSERTION_POINT "1" "0" )
(CHANGE_FLIP (ENTLAST) "STF1"))
)
(INSERT_ADDITIONAL_BLOCKS INSERTION_POINT (NTH I SNAP_POINTS) "UP")
))



(IF (= COLOUR_CODE 6)
(PROGN
(SETQ INSERTION_POINT (LIST (CAR TEMP_ELE) (+ (CADR TEMP_ELE) MAST_LENGTH) 0.0))
(COMMAND "INSERT" "SINGLE_CANT_MAST" INSERTION_POINT "1" "0" )
(SETQ MAST_LIST (CONS (LIST (ENTLAST) INSERTION_POINT) MAST_LIST))
(IF (/= I (- (LENGTH SNAP_POINTS) 1)) (PROGN (MODIFY_ATTRIBUTES (ENTLAST) '("SPAN1") (LIST (RTOS (NTH 1 (NTH I SNAP_POINTS)) 2 2)))
;(INSERT_ATTRIBUTES (ENTLAST) '("SPAN1") (LIST (LIST (+ (CAR INSERTION_POINT) (* (/ (NTH 1 (NTH I SNAP_POINTS)) 2) SCALE))  (+ (CADR INSERTION_POINT) SPAN_REFERENCE) 0.0)))
))

(SETQ IMP_POINT (ADDITION INSERTION_POINT IMP_REFERENCE))
(SETQ STAG_POINT (ADDITION INSERTION_POINT SG_REFERENCE))
(SETQ POINT1 (LIST  (CAR TEMP_ELE)  (+  (CADR TEMP_ELE) 175.00) 0.0))
(INSERT_ATTRIBUTES1 (ENTLAST) (LIST "IMM1") (LIST IMP_POINT))
(INSERT_ATTRIBUTES1 (ENTLAST) (LIST "SGM1") (LIST STAG_POINT))
(CHANGE_DYNAMIC_PROPERTIES (ENTLAST) '("STL1") (LIST MAST_LENGTH))
(INSERT_ATTRIBUTES1 (ENTLAST) (LIST "LOM1") (LIST POINT1))
(CHANGE_TEXT_ALIGNMENT_POINT (ENTLAST) '("FOUNDATION_TYPE1") (LIST (LIST (CAR INSERTION_POINT)  (+ (CADR BS_PT) FDN_REFERENCE_Y) 0.0)))
    (CHANGE_TEXT_ALIGNMENT_POINT (ENTLAST) '("RD1") (LIST (LIST (CAR INSERTION_POINT)  (+ (CADR BS_PT) RD_REFERENCE_Y) 0.0)))
    (CHANGE_TEXT_ALIGNMENT_POINT (ENTLAST) '("TC1") (LIST (LIST (+ (CAR INSERTION_POINT) TC_REFERENCE_X)  (+ (CADR INSERTION_POINT) TC_REFERENCE_Y) 0.0)))
    (CHANGE_VISIBILITY (ENTLAST) (LIST "FOUNDATION_TYPE1" "RD1" "SPAN1" "TC1" ) (LIST (ITOA VISIBILITY_FDN) (ITOA VISIBILITY_RD) (ITOA VISIBILITY_SPAN) (ITOA VISIBILITY_TC)))
(IF (/= (NTH 1 (NTH I SNAP_POINTS)) NIL) (CHANGE_TEXT_ALIGNMENT_POINT (ENTLAST) '("SPAN1") (LIST (LIST (IF (/= (NTH 1 (NTH I SNAP_POINTS)) 0) (+ (CAR INSERTION_POINT) (/ (* (NTH 1 (NTH I SNAP_POINTS)) SCALE) 2)) (+ (CAR INSERTION_POINT) SPAN_REFERENCE_X))  (+ (CADR INSERTION_POINT) SPAN_REFERENCE_Y) 0.0))))

(IF (= FLAG "Y")
(PROGN (COMMAND "INSERT" "SUPER_MAST" INSERTION_POINT "1" "0" )
(CHANGE_FLIP (ENTLAST) "STF1"))
)
(INSERT_ADDITIONAL_BLOCKS INSERTION_POINT (NTH I SNAP_POINTS) "UP")
))

  


(IF (/= (VL-POSITION COLOUR_CODE (LIST 2 1 5)) NIL)
(PROGN
  (SETQ INSERTION_POINT (LIST (CAR TEMP_ELE) (+ (CADR TEMP_ELE) MAST_LENGTH) 0.0))
(COMMAND "INSERT" "DOUBLE_CANT_MAST" INSERTION_POINT "1" "0" )
(SETQ MAST_LIST (CONS (LIST (ENTLAST) INSERTION_POINT) MAST_LIST))
(CHANGE_FLIP (ENTLAST) "STF1")
(COMMAND "MOVE" (ENTLAST) "" (CDR (ASSOC 10 (ENTGET (ENTLAST)))) INSERTION_POINT)
(IF (/= I (- (LENGTH SNAP_POINTS) 1)) (PROGN (MODIFY_ATTRIBUTES (ENTLAST) '("SPAN1" "SPAN2") (LIST (RTOS (NTH 1 (NTH I SNAP_POINTS)) 2 2) (RTOS (NTH 1 (NTH I SNAP_POINTS)) 2 2)))
;(INSERT_ATTRIBUTES (ENTLAST) '("SPAN1" "SPAN2") (LIST (LIST (+ (CAR INSERTION_POINT) (* (/ (NTH 1 (NTH I SNAP_POINTS)) 2) SCALE))  (+ (CADR INSERTION_POINT) SPAN_REFERENCE) 0.0) (LIST (+ (CAR INSERTION_POINT) (/ (NTH 1 (NTH I SNAP_POINTS)) 2))  (+ (+ (CADR INSERTION_POINT) SPAN_REFERENCE) 3) 0.0)))
))
(SETQ IMP_POINT (ADDITION INSERTION_POINT IMP_REFERENCE))
(SETQ STAG_POINT (ADDITION INSERTION_POINT SG_REFERENCE))
(SETQ POINT1 (LIST  (CAR TEMP_ELE)  (+  (CADR TEMP_ELE) 175.00) 0.0))
(INSERT_ATTRIBUTES1 (ENTLAST) (LIST "IMM1") (LIST IMP_POINT))
(INSERT_ATTRIBUTES1 (ENTLAST) (LIST "LOM1") (LIST POINT1))
(CHANGE_DYNAMIC_PROPERTIES (ENTLAST) '("STL1") (LIST MAST_LENGTH))
  (CHANGE_TEXT_ALIGNMENT_POINT (ENTLAST) '("FOUNDATION_TYPE1") (LIST (LIST (CAR INSERTION_POINT)  (+ (CADR BS_PT) FDN_REFERENCE_Y) 0.0)))
    (CHANGE_TEXT_ALIGNMENT_POINT (ENTLAST) '("RD1") (LIST (LIST (CAR INSERTION_POINT)  (+ (CADR BS_PT) RD_REFERENCE_Y) 0.0)))
    (CHANGE_TEXT_ALIGNMENT_POINT (ENTLAST) '("TC1") (LIST (LIST (+ (CAR INSERTION_POINT) TC_REFERENCE_X)  (+ (CADR INSERTION_POINT) TC_REFERENCE_Y) 0.0)))
    (CHANGE_VISIBILITY (ENTLAST) (LIST "FOUNDATION_TYPE1" "RD1" "SPAN1" "TC1" ) (LIST (ITOA VISIBILITY_FDN) (ITOA VISIBILITY_RD) (ITOA VISIBILITY_SPAN) (ITOA VISIBILITY_TC)))
(IF (/= (NTH 1 (NTH I SNAP_POINTS)) NIL) (CHANGE_TEXT_ALIGNMENT_POINT (ENTLAST) '("SPAN1") (LIST (LIST (IF (NTH 1 (NTH I SNAP_POINTS)) (+ (CAR INSERTION_POINT) (* (/ (NTH 1 (NTH I SNAP_POINTS)) 2) SCALE)) (+ (CAR INSERTION_POINT) SPAN_REFERENCE_X))  (+ (CADR INSERTION_POINT) SPAN_REFERENCE_Y) 0.0))))
(INSERT_DYNAMIC_PROPERTIES (ENTLAST) '("STL1" "STL2") (LIST 8.1156 10.6156))
(CHANGE_VISIBILITY (ENTLAST) (LIST "SPAN2" ) (LIST "0"))
(IF (= FLAG "Y")
(PROGN (COMMAND "INSERT" "SUPER_MAST" INSERTION_POINT "1" "0" )
(CHANGE_FLIP (ENTLAST) "STF1"))
)
(INSERT_ADDITIONAL_BLOCKS INSERTION_POINT (NTH I SNAP_POINTS) "UP")
  ))

(SETQ I (+ I 1))
)
(REVERSE MAST_LIST)
)





(DEFUN INSERT_MASTS_DN_NORMAL ( OFFSET_ENTITIES1 TRACK_ENTITY SCALE ENTNAME / ENTNAME SNAP_POINTS I TEMP_ELE INSERTION_POINT MAST_LENGTH VALUES POINT POINT1 IMP_REFERENCE SG_REFERENCE FLAG MAST_LIST IMP_POINT STAG_POINT SPAN_REFERENCE SCALE)
(SETQ SNAP_POINTS (GET_MAST_INSERTION_POINTS_NORMAL OFFSET_ENTITIES1 TRACK_ENTITY SCALE))
(SETQ SNAP_POINTS (INDENTIFY_LOCATIONS SNAP_POINTS "DN"))
(SETQ BS_PT (CDR (ASSOC 10 (ENTGET ENTNAME))))
(SETQ AS (GET_DYNAMIC_PROPERTIES ENTNAME '("STL1" "SGM1 X" "IMM1 X" "SGM1 Y" "IMM1 Y")))
(SETQ MAST_LENGTH (CADR(ASSOC "STL1" AS)))
(SETQ IMP_REFERENCE (LIST (CADR(ASSOC "IMM1 X" AS)) (CADR(ASSOC "IMM1 Y" AS)) 0.0))
(SETQ SG_REFERENCE (LIST (CADR(ASSOC "SGM1 X" AS)) (CADR(ASSOC "SGM1 Y" AS)) 0.0))
(SETQ SPAN_REFERENCE (- (NTH 1 (NTH 2 (ASSOC "SPAN1" (NTH 1 (ASSOC 4 (YARD_STRUCTURE_INFO ENTNAME))))))  (NTH 1 (CDR (ASSOC 10 (ENTGET ENTNAME))))))
  (SETQ FDN_REFERENCE (GET_TEXT_ALIGNMENT_POINT (LIST ENTNAME) "FOUNDATION_TYPE1" 0))
  (SETQ FDN_REFERENCE_X (- (NTH 0 (NTH 1 (NTH 0 FDN_REFERENCE)))  (NTH 0 (CDR (ASSOC 10 (ENTGET ENTNAME))))))
  (SETQ FDN_REFERENCE_Y (- (NTH 1 (NTH 1 (NTH 0 FDN_REFERENCE)))  (NTH 1 (CDR (ASSOC 10 (ENTGET ENTNAME))))))
  (SETQ RD_REFERENCE (GET_TEXT_ALIGNMENT_POINT (LIST ENTNAME) "RD1" 0))
  (SETQ RD_REFERENCE_X (- (NTH 0 (NTH 1 (NTH 0 RD_REFERENCE)))  (NTH 0 (CDR (ASSOC 10 (ENTGET ENTNAME))))))
  (SETQ RD_REFERENCE_Y (- (NTH 1 (NTH 1 (NTH 0 RD_REFERENCE)))  (NTH 1 (CDR (ASSOC 10 (ENTGET ENTNAME))))))
  (SETQ TC_REFERENCE (GET_TEXT_ALIGNMENT_POINT (LIST ENTNAME) "TC1" 0))
  (SETQ TC_REFERENCE_X (- (NTH 0 (NTH 1 (NTH 0 TC_REFERENCE)))  (NTH 0 (CDR (ASSOC 10 (ENTGET ENTNAME))))))
  (SETQ TC_REFERENCE_Y (- (NTH 1 (NTH 1 (NTH 0 TC_REFERENCE)))  (NTH 1 (CDR (ASSOC 10 (ENTGET ENTNAME))))))
  (SETQ SPAN_REFERENCE (GET_TEXT_ALIGNMENT_POINT (LIST ENTNAME) "SPAN1" 0))
  (SETQ SPAN_REFERENCE_X (- (NTH 0 (NTH 1 (NTH 0 SPAN_REFERENCE)))  (NTH 0 (CDR (ASSOC 10 (ENTGET ENTNAME))))))
  (SETQ SPAN_REFERENCE_Y (- (NTH 1 (NTH 1 (NTH 0 SPAN_REFERENCE)))  (NTH 1 (CDR (ASSOC 10 (ENTGET ENTNAME))))))
  (SETQ VISIBILITY_FDN (NTH 0 (SINGLE_ELE_LIST (EXTRACT_ATTRIBUTES ENTNAME (LIST "FOUNDATION_TYPE1" ) 3) 1)))
  (SETQ VISIBILITY_RD (NTH 0 (SINGLE_ELE_LIST (EXTRACT_ATTRIBUTES ENTNAME (LIST "RD1" ) 3) 1)))
  (SETQ VISIBILITY_SPAN (NTH 0 (SINGLE_ELE_LIST (EXTRACT_ATTRIBUTES ENTNAME (LIST "SPAN1" ) 3) 1)))
  (SETQ VISIBILITY_TC (NTH 0 (SINGLE_ELE_LIST (EXTRACT_ATTRIBUTES ENTNAME (LIST "TC1" ) 3) 1)))
(SETQ FLAG "Y")
(SETQ MAST_LIST NIL)
(SETQ I 0)
(WHILE (< I (LENGTH SNAP_POINTS))
(SETQ TEMP_ELE (NTH 0 (NTH I SNAP_POINTS)))
(SETQ COLOUR_CODE (CDR (ASSOC 62  (ENTGET (NTH 0 (NTH 2 (NTH I SNAP_POINTS)))))))
(IF (/= (VL-POSITION COLOUR_CODE (LIST 3 8 9)) NIL)
(PROGN
(SETQ INSERTION_POINT (LIST (CAR TEMP_ELE) (- (CADR TEMP_ELE) MAST_LENGTH) 0.0))
(COMMAND "INSERT" "SINGLE_CANT_MAST" INSERTION_POINT "1" "0" )
(SETQ MAST_LIST (CONS (LIST (ENTLAST) INSERTION_POINT) MAST_LIST))
(CHANGE_FLIP (ENTLAST) "STF1")
(COMMAND "MOVE" (ENTLAST) "" (CDR (ASSOC 10 (ENTGET (ENTLAST)))) INSERTION_POINT)
(IF (/= I (- (LENGTH SNAP_POINTS) 1)) (PROGN (MODIFY_ATTRIBUTES (ENTLAST) '("SPAN1") (LIST (RTOS (NTH 1 (NTH I SNAP_POINTS)) 2 2)))
;(INSERT_ATTRIBUTES (ENTLAST) '("SPAN1") (LIST (LIST (+ (CAR INSERTION_POINT) (* (/ (NTH 1 (NTH I SNAP_POINTS)) 2) SCALE))  (+ (CADR INSERTION_POINT) SPAN_REFERENCE) 0.0)))
))
(SETQ IMP_POINT (ADDITION INSERTION_POINT IMP_REFERENCE))
(SETQ STAG_POINT (ADDITION INSERTION_POINT SG_REFERENCE))
(SETQ POINT1 (LIST  (CAR TEMP_ELE)  (-  (CADR TEMP_ELE) 185.00) 0.0))
(INSERT_ATTRIBUTES1 (ENTLAST) (LIST "IMM1") (LIST IMP_POINT))
(INSERT_ATTRIBUTES1 (ENTLAST) (LIST "SGM1") (LIST STAG_POINT))
(CHANGE_DYNAMIC_PROPERTIES (ENTLAST) '("STL1") (LIST MAST_LENGTH))
(INSERT_ATTRIBUTES1 (ENTLAST) (LIST "LOM1") (LIST POINT1))
(CHANGE_TEXT_ALIGNMENT_POINT (ENTLAST) '("FOUNDATION_TYPE1") (LIST (LIST (CAR INSERTION_POINT)  (+ (CADR BS_PT) FDN_REFERENCE_Y) 0.0)))
    (CHANGE_TEXT_ALIGNMENT_POINT (ENTLAST) '("RD1") (LIST (LIST (CAR INSERTION_POINT)  (+ (CADR BS_PT) RD_REFERENCE_Y) 0.0)))
    (CHANGE_TEXT_ALIGNMENT_POINT (ENTLAST) '("TC1") (LIST (LIST (+ (CAR INSERTION_POINT) TC_REFERENCE_X)  (+ (CADR INSERTION_POINT) TC_REFERENCE_Y) 0.0)))
    (CHANGE_VISIBILITY (ENTLAST) (LIST "FOUNDATION_TYPE1" "RD1" "SPAN1" "TC1" ) (LIST (ITOA VISIBILITY_FDN) (ITOA VISIBILITY_RD) (ITOA VISIBILITY_SPAN) (ITOA VISIBILITY_TC)))
(IF (/= (NTH 1 (NTH I SNAP_POINTS)) NIL) (CHANGE_TEXT_ALIGNMENT_POINT (ENTLAST) '("SPAN1") (LIST (LIST (IF (/= (NTH 1 (NTH I SNAP_POINTS)) 0) (+ (CAR INSERTION_POINT) (/ (* (NTH 1 (NTH I SNAP_POINTS)) SCALE) 2)) (+ (CAR INSERTION_POINT) SPAN_REFERENCE_X))  (+ (CADR INSERTION_POINT) SPAN_REFERENCE_Y) 0.0))))

(IF (= FLAG "Y")
(PROGN (COMMAND "INSERT" "SUPER_MAST" INSERTION_POINT "1" "0" )
))
(INSERT_ADDITIONAL_BLOCKS INSERTION_POINT (NTH I SNAP_POINTS) "DN")
))

(IF (= COLOUR_CODE 7)
(PROGN
(SETQ INSERTION_POINT (LIST (CAR TEMP_ELE) (- (CADR TEMP_ELE) MAST_LENGTH) 0.0))
(COMMAND "INSERT" "SINGLE_CANT_MAST" INSERTION_POINT "1" "0" )
(SETQ MAST_LIST (CONS (LIST (ENTLAST) INSERTION_POINT) MAST_LIST))
(CHANGE_FLIP (ENTLAST) "STF1")
(COMMAND "MOVE" (ENTLAST) "" (CDR (ASSOC 10 (ENTGET (ENTLAST)))) INSERTION_POINT)
(IF (/= I (- (LENGTH SNAP_POINTS) 1)) (PROGN (MODIFY_ATTRIBUTES (ENTLAST) '("SPAN1") (LIST (RTOS (NTH 1 (NTH I SNAP_POINTS)) 2 2)))
;(INSERT_ATTRIBUTES (ENTLAST) '("SPAN1") (LIST (LIST (+ (CAR INSERTION_POINT) (* (/ (NTH 1 (NTH I SNAP_POINTS)) 2) SCALE))  (+ (CADR INSERTION_POINT) SPAN_REFERENCE) 0.0)))
))
(SETQ IMP_POINT (ADDITION INSERTION_POINT IMP_REFERENCE))
(SETQ STAG_POINT (ADDITION INSERTION_POINT SG_REFERENCE))
(SETQ POINT1 (LIST  (CAR TEMP_ELE)  (-  (CADR TEMP_ELE) 185.00) 0.0))
(INSERT_ATTRIBUTES1 (ENTLAST) (LIST "IMM1") (LIST IMP_POINT))
(INSERT_ATTRIBUTES1 (ENTLAST) (LIST "SGM1") (LIST STAG_POINT))
(CHANGE_DYNAMIC_PROPERTIES (ENTLAST) '("STL1") (LIST MAST_LENGTH))
(INSERT_ATTRIBUTES1 (ENTLAST) (LIST "LOM1") (LIST POINT1))
(CHANGE_TEXT_ALIGNMENT_POINT (ENTLAST) '("FOUNDATION_TYPE1") (LIST (LIST (CAR INSERTION_POINT)  (+ (CADR BS_PT) FDN_REFERENCE_Y) 0.0)))
    (CHANGE_TEXT_ALIGNMENT_POINT (ENTLAST) '("RD1") (LIST (LIST (CAR INSERTION_POINT)  (+ (CADR BS_PT) RD_REFERENCE_Y) 0.0)))
    (CHANGE_TEXT_ALIGNMENT_POINT (ENTLAST) '("TC1") (LIST (LIST (+ (CAR INSERTION_POINT) TC_REFERENCE_X)  (+ (CADR INSERTION_POINT) TC_REFERENCE_Y) 0.0)))
    (CHANGE_VISIBILITY (ENTLAST) (LIST "FOUNDATION_TYPE1" "RD1" "SPAN1" "TC1" ) (LIST (ITOA VISIBILITY_FDN) (ITOA VISIBILITY_RD) (ITOA VISIBILITY_SPAN) (ITOA VISIBILITY_TC)))
(IF (/= (NTH 1 (NTH I SNAP_POINTS)) NIL) (CHANGE_TEXT_ALIGNMENT_POINT (ENTLAST) '("SPAN1") (LIST (LIST (IF (/= (NTH 1 (NTH I SNAP_POINTS)) 0) (+ (CAR INSERTION_POINT) (/ (* (NTH 1 (NTH I SNAP_POINTS)) SCALE) 2)) (+ (CAR INSERTION_POINT) SPAN_REFERENCE_X))  (+ (CADR INSERTION_POINT) SPAN_REFERENCE_Y) 0.0))))
(IF (= FLAG "Y")
(PROGN (COMMAND "INSERT" "SUPER_MAST" INSERTION_POINT "1" "0" )
))
(INSERT_ADDITIONAL_BLOCKS INSERTION_POINT (NTH I SNAP_POINTS) "DN")
))


(IF (= COLOUR_CODE 4)
(PROGN
(SETQ INSERTION_POINT (LIST (CAR TEMP_ELE) (- (CADR TEMP_ELE) MAST_LENGTH) 0.0))
(COMMAND "INSERT" "SINGLE_CANT_MAST" INSERTION_POINT "1" "0" )
(SETQ MAST_LIST (CONS (LIST (ENTLAST) INSERTION_POINT) MAST_LIST))
(CHANGE_FLIP (ENTLAST) "STF1")
(COMMAND "MOVE" (ENTLAST) "" (CDR (ASSOC 10 (ENTGET (ENTLAST)))) INSERTION_POINT)
(IF (/= I (- (LENGTH SNAP_POINTS) 1)) (PROGN (MODIFY_ATTRIBUTES (ENTLAST) '("SPAN1") (LIST (RTOS (NTH 1 (NTH I SNAP_POINTS)) 2 2)))
;(INSERT_ATTRIBUTES (ENTLAST) '("SPAN1") (LIST (LIST (+ (CAR INSERTION_POINT) (* (/ (NTH 1 (NTH I SNAP_POINTS)) 2) SCALE))  (+ (CADR INSERTION_POINT) SPAN_REFERENCE) 0.0)))
))
(SETQ IMP_POINT (ADDITION INSERTION_POINT IMP_REFERENCE))
(SETQ STAG_POINT (ADDITION INSERTION_POINT SG_REFERENCE))
(SETQ POINT1 (LIST  (CAR TEMP_ELE)  (-  (CADR TEMP_ELE) 185.00) 0.0))
(INSERT_ATTRIBUTES1 (ENTLAST) (LIST "IMM1") (LIST IMP_POINT))
(INSERT_ATTRIBUTES1 (ENTLAST) (LIST "SGM1") (LIST STAG_POINT))
(CHANGE_DYNAMIC_PROPERTIES (ENTLAST) '("STL1") (LIST MAST_LENGTH))
(INSERT_ATTRIBUTES1 (ENTLAST) (LIST "LOM1") (LIST POINT1))
(CHANGE_TEXT_ALIGNMENT_POINT (ENTLAST) '("FOUNDATION_TYPE1") (LIST (LIST (CAR INSERTION_POINT)  (+ (CADR BS_PT) FDN_REFERENCE_Y) 0.0)))
    (CHANGE_TEXT_ALIGNMENT_POINT (ENTLAST) '("RD1") (LIST (LIST (CAR INSERTION_POINT)  (+ (CADR BS_PT) RD_REFERENCE_Y) 0.0)))
    (CHANGE_TEXT_ALIGNMENT_POINT (ENTLAST) '("TC1") (LIST (LIST (+ (CAR INSERTION_POINT) TC_REFERENCE_X)  (+ (CADR INSERTION_POINT) TC_REFERENCE_Y) 0.0)))
    (CHANGE_VISIBILITY (ENTLAST) (LIST "FOUNDATION_TYPE1" "RD1" "SPAN1" "TC1" ) (LIST (ITOA VISIBILITY_FDN) (ITOA VISIBILITY_RD) (ITOA VISIBILITY_SPAN) (ITOA VISIBILITY_TC)))
(IF (/= (NTH 1 (NTH I SNAP_POINTS)) NIL) (CHANGE_TEXT_ALIGNMENT_POINT (ENTLAST) '("SPAN1") (LIST (LIST (IF (/= (NTH 1 (NTH I SNAP_POINTS)) 0) (+ (CAR INSERTION_POINT) (/ (* (NTH 1 (NTH I SNAP_POINTS)) SCALE) 2)) (+ (CAR INSERTION_POINT) SPAN_REFERENCE_X))  (+ (CADR INSERTION_POINT) SPAN_REFERENCE_Y) 0.0))))
(IF (= FLAG "Y")
(PROGN (COMMAND "INSERT" "SUPER_MAST" INSERTION_POINT "1" "0" )
))
(INSERT_ADDITIONAL_BLOCKS INSERTION_POINT (NTH I SNAP_POINTS) "DN")
))


(IF (= COLOUR_CODE 6)
(PROGN
(SETQ INSERTION_POINT (LIST (CAR TEMP_ELE) (- (CADR TEMP_ELE) MAST_LENGTH) 0.0))
(COMMAND "INSERT" "SINGLE_CANT_MAST" INSERTION_POINT "1" "0" )
(SETQ MAST_LIST (CONS (LIST (ENTLAST) INSERTION_POINT) MAST_LIST))
(CHANGE_FLIP (ENTLAST) "STF1")
(COMMAND "MOVE" (ENTLAST) "" (CDR (ASSOC 10 (ENTGET (ENTLAST)))) INSERTION_POINT)
(IF (/= I (- (LENGTH SNAP_POINTS) 1)) (PROGN (MODIFY_ATTRIBUTES (ENTLAST) '("SPAN1") (LIST (RTOS (NTH 1 (NTH I SNAP_POINTS)) 2 2)))
;(INSERT_ATTRIBUTES (ENTLAST) '("SPAN1") (LIST (LIST (+ (CAR INSERTION_POINT) (* (/ (NTH 1 (NTH I SNAP_POINTS)) 2) SCALE))  (+ (CADR INSERTION_POINT) SPAN_REFERENCE) 0.0)))
))
(SETQ IMP_POINT (ADDITION INSERTION_POINT IMP_REFERENCE))
(SETQ STAG_POINT (ADDITION INSERTION_POINT SG_REFERENCE))
(SETQ POINT1 (LIST  (CAR TEMP_ELE)  (-  (CADR TEMP_ELE) 185.00) 0.0))
(INSERT_ATTRIBUTES1 (ENTLAST) (LIST "IMM1") (LIST IMP_POINT))
(INSERT_ATTRIBUTES1 (ENTLAST) (LIST "SGM1") (LIST STAG_POINT))
(CHANGE_DYNAMIC_PROPERTIES (ENTLAST) '("STL1") (LIST MAST_LENGTH))
(INSERT_ATTRIBUTES1 (ENTLAST) (LIST "LOM1") (LIST POINT1))
(CHANGE_TEXT_ALIGNMENT_POINT (ENTLAST) '("FOUNDATION_TYPE1") (LIST (LIST (CAR INSERTION_POINT)  (+ (CADR BS_PT) FDN_REFERENCE_Y) 0.0)))
    (CHANGE_TEXT_ALIGNMENT_POINT (ENTLAST) '("RD1") (LIST (LIST (CAR INSERTION_POINT)  (+ (CADR BS_PT) RD_REFERENCE_Y) 0.0)))
    (CHANGE_TEXT_ALIGNMENT_POINT (ENTLAST) '("TC1") (LIST (LIST (+ (CAR INSERTION_POINT) TC_REFERENCE_X)  (+ (CADR INSERTION_POINT) TC_REFERENCE_Y) 0.0)))
    (CHANGE_VISIBILITY (ENTLAST) (LIST "FOUNDATION_TYPE1" "RD1" "SPAN1" "TC1" ) (LIST (ITOA VISIBILITY_FDN) (ITOA VISIBILITY_RD) (ITOA VISIBILITY_SPAN) (ITOA VISIBILITY_TC)))
(IF (/= (NTH 1 (NTH I SNAP_POINTS)) NIL) (CHANGE_TEXT_ALIGNMENT_POINT (ENTLAST) '("SPAN1") (LIST (LIST (IF (/= (NTH 1 (NTH I SNAP_POINTS)) 0) (+ (CAR INSERTION_POINT) (/ (* (NTH 1 (NTH I SNAP_POINTS)) SCALE) 2)) (+ (CAR INSERTION_POINT) SPAN_REFERENCE_X))  (+ (CADR INSERTION_POINT) SPAN_REFERENCE_Y) 0.0))))
(IF (= FLAG "Y")
(PROGN (COMMAND "INSERT" "SUPER_MAST" INSERTION_POINT "1" "0" )
))
(INSERT_ADDITIONAL_BLOCKS INSERTION_POINT (NTH I SNAP_POINTS) "DN")
))




(IF (/= (VL-POSITION COLOUR_CODE (LIST 2 1 5)) NIL)
(PROGN
  (SETQ INSERTION_POINT (LIST (CAR TEMP_ELE) (- (CADR TEMP_ELE) MAST_LENGTH) 0.0))
(COMMAND "INSERT" "DOUBLE_CANT_MAST" INSERTION_POINT "1" "0" )
(SETQ MAST_LIST (CONS (LIST (ENTLAST) INSERTION_POINT) MAST_LIST))
(IF (/= I (- (LENGTH SNAP_POINTS) 1)) (PROGN (MODIFY_ATTRIBUTES (ENTLAST) '("SPAN1" "SPAN2") (LIST (RTOS (NTH 1 (NTH I SNAP_POINTS)) 2 2) (RTOS (NTH 1 (NTH I SNAP_POINTS)) 2 2)))
;(INSERT_ATTRIBUTES (ENTLAST) '("SPAN1" "SPAN2") (LIST (LIST (+ (CAR INSERTION_POINT) (* (/ (NTH 1 (NTH I SNAP_POINTS)) 2) SCALE))  (+ (CADR INSERTION_POINT) SPAN_REFERENCE) 0.0) (LIST (+ (CAR INSERTION_POINT) (/ (NTH 1 (NTH I SNAP_POINTS)) 2))  (+ (+ (CADR INSERTION_POINT) SPAN_REFERENCE) 3) 0.0)))
))
(SETQ IMP_POINT (ADDITION INSERTION_POINT IMP_REFERENCE))
(SETQ STAG_POINT (ADDITION INSERTION_POINT SG_REFERENCE))
 (SETQ POINT1 (LIST  (CAR TEMP_ELE)  (-  (CADR TEMP_ELE) 185.00) 0.0))
(INSERT_ATTRIBUTES1 (ENTLAST) (LIST "IMM1") (LIST IMP_POINT))
 (INSERT_ATTRIBUTES1 (ENTLAST) (LIST "LOM1") (LIST POINT1))
  (CHANGE_TEXT_ALIGNMENT_POINT (ENTLAST) '("FOUNDATION_TYPE1") (LIST (LIST (CAR INSERTION_POINT)  (+ (CADR BS_PT) FDN_REFERENCE_Y) 0.0)))
    (CHANGE_TEXT_ALIGNMENT_POINT (ENTLAST) '("RD1") (LIST (LIST (CAR INSERTION_POINT)  (+ (CADR BS_PT) RD_REFERENCE_Y) 0.0)))
    (CHANGE_TEXT_ALIGNMENT_POINT (ENTLAST) '("TC1") (LIST (LIST (+ (CAR INSERTION_POINT) TC_REFERENCE_X)  (+ (CADR INSERTION_POINT) TC_REFERENCE_Y) 0.0)))
    (CHANGE_VISIBILITY (ENTLAST) (LIST "FOUNDATION_TYPE1" "RD1" "SPAN1" "TC1" ) (LIST (ITOA VISIBILITY_FDN) (ITOA VISIBILITY_RD) (ITOA VISIBILITY_SPAN) (ITOA VISIBILITY_TC)))
(IF (/= (NTH 1 (NTH I SNAP_POINTS)) NIL) (CHANGE_TEXT_ALIGNMENT_POINT (ENTLAST) '("SPAN1") (LIST (LIST (IF (NTH 1 (NTH I SNAP_POINTS)) (+ (CAR INSERTION_POINT) (/ (* (NTH 1 (NTH I SNAP_POINTS)) SCALE) 2)) (+ (CAR INSERTION_POINT) SPAN_REFERENCE_X))  (+ (CADR INSERTION_POINT) SPAN_REFERENCE_Y) 0.0))))
(INSERT_DYNAMIC_PROPERTIES (ENTLAST) '("STL1" "STL2") (LIST 10.6156 8.1156))
(CHANGE_VISIBILITY (ENTLAST) (LIST "SPAN2" ) (LIST "0"))
 (IF (= FLAG "Y")
 (PROGN (COMMAND "INSERT" "SUPER_MAST" INSERTION_POINT "1" "0" )
))
(INSERT_ADDITIONAL_BLOCKS INSERTION_POINT (NTH I SNAP_POINTS) "DN")
  ))
(SETQ I (+ I 1))
)(REVERSE MAST_LIST)
)






(DEFUN INSERT_ADDITIONAL_BLOCKS ( MAIN_BLOCK_INSERTION_POINT INFO TRACK_TYPE / INDENTIFICATION_STRING WIRE_NUMBER1 WIRE_NUMBER2  )
  (SETQ INDENTIFICATION_STRING (NTH 3 INFO))
  (SETQ WIRE_NUMBER1 (NTH 4 INFO))
  (SETQ WIRE_NUMBER2 (NTH 5 INFO))
  (SETQ NA 0)
  (IF (= TRACK_TYPE "UP")
  (PROGN
  (IF (= INDENTIFICATION_STRING "BWA_END")
    (PROGN
      (COMMAND "INSERT" "ANCHOR" MAIN_BLOCK_INSERTION_POINT "1" "0" )
      (INSERT_DYNAMIC_PROPERTIES (ENTLAST) '("LENGTHEN") (LIST 4.00))
      (INSERT_ATTRIBUTES (ENTLAST) '("WIRE_RUN1") (LIST (LIST (+ (CAR MAIN_BLOCK_INSERTION_POINT) 11.40)  (- (CADR MAIN_BLOCK_INSERTION_POINT) 4.35) 0.0)))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (COMMAND "INSERT" "TENSION_LENGTH" (LIST (CAR MAIN_BLOCK_INSERTION_POINT) (+ (CADR MAIN_BLOCK_INSERTION_POINT) 70) 0.0) "1" "0" )
      (COMMAND "INSERT" "JUMPER" (LIST (- (CAR MAIN_BLOCK_INSERTION_POINT) 14.786) (- (CADR MAIN_BLOCK_INSERTION_POINT) 3.2401) 0.0) "1" "0" )
      (INSERT_DYNAMIC_PROPERTIES (ENTLAST) '("Visibility1" "Angle1") (LIST "ATJ" (* 1 (/ PI 3))))
      (MODIFY_ATTRIBUTES (ENTLAST) (LIST "JUMPER_TYPE2") (LIST "3ATJ"))
    )
  )

  (IF (= INDENTIFICATION_STRING "BWA_START")
    (PROGN
      (COMMAND "INSERT" "ANCHOR" MAIN_BLOCK_INSERTION_POINT "1" "0" )
      (INSERT_DYNAMIC_PROPERTIES (ENTLAST) '("LENGTHEN") (LIST 4.00))
      (CHANGE_FLIP (ENTLAST) "ANF1")
      (INSERT_ATTRIBUTES (ENTLAST) '("WIRE_RUN1") (LIST (LIST (- (CAR MAIN_BLOCK_INSERTION_POINT) 16.00)  (- (CADR MAIN_BLOCK_INSERTION_POINT) 5.75) 0.0)))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (COMMAND "INSERT" "TENSION_LENGTH" (LIST (CAR MAIN_BLOCK_INSERTION_POINT) (+ (CADR MAIN_BLOCK_INSERTION_POINT) 70) 0.0) "1" "0" )
      (CHANGE_FLIP (ENTLAST) "TLF2")
      (INSERT_DYNAMIC_PROPERTIES (ENTLAST) '("TLM4 X") (LIST (+ (NTH 1 (NTH 0 (GET_DYNAMIC_PROPERTIES (ENTLAST) '("TLM4 X")))) 24.00)))
      (COMMAND "INSERT" "JUMPER" (LIST (+ (CAR MAIN_BLOCK_INSERTION_POINT) 14.786) (- (CADR MAIN_BLOCK_INSERTION_POINT) 3.2401) 0.0) "1" "0" )
      (INSERT_DYNAMIC_PROPERTIES (ENTLAST) '("Visibility1" "Angle1") (LIST "ATJ" (* 2 (/ PI 3))))
      (MODIFY_ATTRIBUTES (ENTLAST) (LIST "JUMPER_TYPE2") (LIST "3ATJ"))
    )
  )


  (IF (= INDENTIFICATION_STRING "ACA_END")
    (PROGN
      (COMMAND "INSERT" "ANCHOR" MAIN_BLOCK_INSERTION_POINT "1" "0" )
      (MODIFY_ATTRIBUTES (ENTLAST) (LIST "ANCHOR_TYPE1") (LIST "ACA"))
      (INSERT_ATTRIBUTES (ENTLAST) '("WIRE_RUN1") (LIST (LIST (+ (CAR MAIN_BLOCK_INSERTION_POINT) 11.40)  (- (CADR MAIN_BLOCK_INSERTION_POINT) 4.35) 0.0)))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (INSERT_DYNAMIC_PROPERTIES (ENTLAST) '("LENGTHEN" "Visibility1") (LIST 4.00 "WITHOUT WEIGHTS"))
    )
  )


  (IF (= INDENTIFICATION_STRING "ACA_START")
    (PROGN
      (COMMAND "INSERT" "ANCHOR" MAIN_BLOCK_INSERTION_POINT "1" "0" )
      (INSERT_DYNAMIC_PROPERTIES (ENTLAST) '("LENGTHEN") (LIST 4.00))
      (CHANGE_FLIP (ENTLAST) "ANF1")
      (MODIFY_ATTRIBUTES (ENTLAST) (LIST "ANCHOR_TYPE1") (LIST "ACA"))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (INSERT_DYNAMIC_PROPERTIES (ENTLAST) '("LENGTHEN" "Visibility1") (LIST 4.00 "WITHOUT WEIGHTS"))
      (INSERT_ATTRIBUTES (ENTLAST) '("WIRE_RUN1") (LIST (LIST (- (CAR MAIN_BLOCK_INSERTION_POINT) 16.00)  (- (CADR MAIN_BLOCK_INSERTION_POINT) 5.75) 0.0)))
    )
  )



  (IF (= INDENTIFICATION_STRING "OLC")
    (PROGN
      (COMMAND "INSERT" "OLC" (LIST  (CAR MAIN_BLOCK_INSERTION_POINT)  (+ (CADR MAIN_BLOCK_INSERTION_POINT) 90.00) 0.0) "1" "0")
      (MODIFY_ATTRIBUTES (ENTLAST) (LIST "TRACK") (LIST "FOR DN MAIN"))
      (COMMAND "INSERT" "JUMPER" (LIST (- (CAR MAIN_BLOCK_INSERTION_POINT) 36.00) (- (CADR MAIN_BLOCK_INSERTION_POINT) 9.75) 0.0) "1" "0" )
      (INSERT_DYNAMIC_PROPERTIES (ENTLAST) '("Visibility1" "JUR1") (LIST "DOUBLE_LINE" (* 110 (/ PI 180))))
      (MODIFY_ATTRIBUTES (ENTLAST) (LIST "JUMPER_TYPE1") (LIST "G"))
    )
  )

  (IF (/= (VL-POSITION INDENTIFICATION_STRING (LIST "ACC" "ACCFA" "ACCAEWA")) NIL)
    (PROGN
      (IF (= INDENTIFICATION_STRING "ACC") (COMMAND "INSERT" "ACC" (LIST  (CAR MAIN_BLOCK_INSERTION_POINT)  (+ (CADR MAIN_BLOCK_INSERTION_POINT) 56.6) 0.0) "1" "0"))
      (IF (= INDENTIFICATION_STRING "ACCFA")
      (PROGN
      (COMMAND "INSERT" "ACC" (LIST  (CAR MAIN_BLOCK_INSERTION_POINT)  (+ (CADR MAIN_BLOCK_INSERTION_POINT) 70) 0.0) "1" "0")
      (COMMAND "INSERT" "BTB_ANC" MAIN_BLOCK_INSERTION_POINT "1" "0")
      (MODIFY_ATTRIBUTES (ENTLAST) (LIST "ANCHOR_TYPE1" "ANCHOR_TYPE2") (LIST "FA" "FA"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (INSERT_DYNAMIC_PROPERTIES (ENTLAST) '("Visibility1") (LIST "WITHOUT WEIGHTS"))
      (COMMAND "INSERT" "JUMPER" MAIN_BLOCK_INSERTION_POINT "1" "0")
      (INSERT_DYNAMIC_PROPERTIES (ENTLAST) '("Visibility1") (LIST "FJ/AEWA"))
      (MODIFY_ATTRIBUTES (ENTLAST) (LIST "JUMPER_TYPE1") (LIST "FJ"))
      (COMMAND "INSERT" "TENSION_LENGTH" (LIST (CAR MAIN_BLOCK_INSERTION_POINT) (+ (CADR MAIN_BLOCK_INSERTION_POINT) 52.00) 0.0) "1" "0")
      (COMMAND "INSERT" "TENSION_LENGTH" (LIST (CAR MAIN_BLOCK_INSERTION_POINT) (+ (CADR MAIN_BLOCK_INSERTION_POINT) 52.00) 0.0) "1" "0" )
      (CHANGE_FLIP (ENTLAST) "TLF2")
      (INSERT_DYNAMIC_PROPERTIES (ENTLAST) '("TLM4 X") (LIST (+ (NTH 1 (NTH 0 (GET_DYNAMIC_PROPERTIES (ENTLAST) '("TLM4 X")))) 24.00)))
      )
      )
      (IF (= INDENTIFICATION_STRING "ACCAEWA")
      (PROGN
      (COMMAND "INSERT" "ACC" (LIST  (CAR MAIN_BLOCK_INSERTION_POINT)  (+ (CADR MAIN_BLOCK_INSERTION_POINT) 70) 0.0) "1" "0")
      (COMMAND "INSERT" "BTB_ANC" MAIN_BLOCK_INSERTION_POINT "1" "0")
      (MODIFY_ATTRIBUTES (ENTLAST) (LIST "ANCHOR_TYPE1" "ANCHOR_TYPE2") (LIST "AEWA" "AEWA"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (INSERT_DYNAMIC_PROPERTIES (ENTLAST) '("Visibility1") (LIST "WITHOUT WEIGHTS"))
      (COMMAND "INSERT" "JUMPER" MAIN_BLOCK_INSERTION_POINT "1" "0")
      (INSERT_DYNAMIC_PROPERTIES (ENTLAST) '("Visibility1") (LIST "FJ/AEWA"))
      (MODIFY_ATTRIBUTES (ENTLAST) (LIST "JUMPER_TYPE1") (LIST "FJ"))
      (COMMAND "INSERT" "TENSION_LENGTH" (LIST (CAR MAIN_BLOCK_INSERTION_POINT) (+ (CADR MAIN_BLOCK_INSERTION_POINT) 52.00) 0.0) "1" "0")
      (COMMAND "INSERT" "TENSION_LENGTH" (LIST (CAR MAIN_BLOCK_INSERTION_POINT) (+ (CADR MAIN_BLOCK_INSERTION_POINT) 52.00) 0.0) "1" "0" )
      (CHANGE_FLIP (ENTLAST) "TLF2")
      (INSERT_DYNAMIC_PROPERTIES (ENTLAST) '("TLM4 X") (LIST (+ (NTH 1 (NTH 0 (GET_DYNAMIC_PROPERTIES (ENTLAST) '("TLM4 X")))) 24.00)))
      )
      )
      (COMMAND "INSERT" "JUMPER" (LIST (- (CAR MAIN_BLOCK_INSERTION_POINT) 4.20) (- (CADR MAIN_BLOCK_INSERTION_POINT) 11.70) 0.0) "1" "0" )
      (INSERT_DYNAMIC_PROPERTIES (ENTLAST) '("Visibility1" "JUR1") (LIST "SINGLE_LINE" (* 240 (/ PI 180))))
      (MODIFY_ATTRIBUTES (ENTLAST) (LIST "JUMPER_TYPE1") (LIST "H"))
    )
  )


  (IF (/= (VL-POSITION INDENTIFICATION_STRING (LIST "AEWA" "DAEWA" "OLCAEWA")) NIL) 
    (PROGN
      (COMMAND "INSERT" "BTB_ANC" MAIN_BLOCK_INSERTION_POINT "1" "0")
      (MODIFY_ATTRIBUTES (ENTLAST) (LIST "ANCHOR_TYPE1" "ANCHOR_TYPE2") (LIST "AEWA" "AEWA"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (INSERT_DYNAMIC_PROPERTIES (ENTLAST) '("Visibility1") (LIST "WITHOUT WEIGHTS"))
      (COMMAND "INSERT" "JUMPER" MAIN_BLOCK_INSERTION_POINT "1" "0")
      (INSERT_DYNAMIC_PROPERTIES (ENTLAST) '("Visibility1") (LIST "FJ/AEWA"))
      (MODIFY_ATTRIBUTES (ENTLAST) (LIST "JUMPER_TYPE1") (LIST "AEWJ"))
      (IF (/= (VL-POSITION INDENTIFICATION_STRING (LIST "AEWA" "DAEWA")) NIL)
      (PROGN
      (COMMAND "INSERT" "TENSION_LENGTH" (LIST (CAR MAIN_BLOCK_INSERTION_POINT) (+ (CADR MAIN_BLOCK_INSERTION_POINT) 70.00) 0.0) "1" "0")
      (COMMAND "INSERT" "TENSION_LENGTH" (LIST (CAR MAIN_BLOCK_INSERTION_POINT) (+ (CADR MAIN_BLOCK_INSERTION_POINT) 70.00) 0.0) "1" "0" )
      (CHANGE_FLIP (ENTLAST) "TLF2")
      (INSERT_DYNAMIC_PROPERTIES (ENTLAST) '("TLM4 X") (LIST (+ (NTH 1 (NTH 0 (GET_DYNAMIC_PROPERTIES (ENTLAST) '("TLM4 X")))) 24.00)))
      )
      (PROGN
      (COMMAND "INSERT" "TENSION_LENGTH" (LIST (CAR MAIN_BLOCK_INSERTION_POINT) (+ (CADR MAIN_BLOCK_INSERTION_POINT) 100.00) 0.0) "1" "0")
      (COMMAND "INSERT" "TENSION_LENGTH" (LIST (CAR MAIN_BLOCK_INSERTION_POINT) (+ (CADR MAIN_BLOCK_INSERTION_POINT) 100.00) 0.0) "1" "0" )
      (CHANGE_FLIP (ENTLAST) "TLF2")
      (INSERT_DYNAMIC_PROPERTIES (ENTLAST) '("TLM4 X") (LIST (+ (NTH 1 (NTH 0 (GET_DYNAMIC_PROPERTIES (ENTLAST) '("TLM4 X")))) 24.00)))
      (COMMAND "INSERT" "OLC" (LIST  (CAR MAIN_BLOCK_INSERTION_POINT)  (+ (CADR MAIN_BLOCK_INSERTION_POINT) 79.00) 0.0) "1" "0")
      (MODIFY_ATTRIBUTES (ENTLAST) (LIST "TRACK") (LIST "FOR DN MAIN"))
      (COMMAND "INSERT" "JUMPER" (LIST (- (CAR MAIN_BLOCK_INSERTION_POINT) 36.00) (- (CADR MAIN_BLOCK_INSERTION_POINT) 9.75) 0.0) "1" "0" )
      (INSERT_DYNAMIC_PROPERTIES (ENTLAST) '("Visibility1" "JUR1") (LIST "DOUBLE_LINE" (* 110 (/ PI 180))))
      (MODIFY_ATTRIBUTES (ENTLAST) (LIST "JUMPER_TYPE1") (LIST "G"))
      )
      )
    )
  )


 (IF (/= (VL-POSITION INDENTIFICATION_STRING (LIST "FA" "DFA" "OLCFA")) NIL) 
    (PROGN
      (COMMAND "INSERT" "BTB_ANC" MAIN_BLOCK_INSERTION_POINT "1" "0")
      (MODIFY_ATTRIBUTES (ENTLAST) (LIST "ANCHOR_TYPE1" "ANCHOR_TYPE2") (LIST "FA" "FA"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (INSERT_DYNAMIC_PROPERTIES (ENTLAST) '("Visibility1") (LIST "WITHOUT WEIGHTS"))
      (COMMAND "INSERT" "JUMPER" MAIN_BLOCK_INSERTION_POINT "1" "0")
      (INSERT_DYNAMIC_PROPERTIES (ENTLAST) '("Visibility1") (LIST "FJ/AEWA"))
      (MODIFY_ATTRIBUTES (ENTLAST) (LIST "JUMPER_TYPE1") (LIST "FJ"))
      (IF (/= (VL-POSITION INDENTIFICATION_STRING (LIST "FA" "DFA")) NIL)
      (PROGN
      (COMMAND "INSERT" "TENSION_LENGTH" (LIST (CAR MAIN_BLOCK_INSERTION_POINT) (+ (CADR MAIN_BLOCK_INSERTION_POINT) 70.00) 0.0) "1" "0")
      (COMMAND "INSERT" "TENSION_LENGTH" (LIST (CAR MAIN_BLOCK_INSERTION_POINT) (+ (CADR MAIN_BLOCK_INSERTION_POINT) 70.00) 0.0) "1" "0" )
      (CHANGE_FLIP (ENTLAST) "TLF2")
      (INSERT_DYNAMIC_PROPERTIES (ENTLAST) '("TLM4 X") (LIST (+ (NTH 1 (NTH 0 (GET_DYNAMIC_PROPERTIES (ENTLAST) '("TLM4 X")))) 24.00)))
      )
      (PROGN
      (COMMAND "INSERT" "TENSION_LENGTH" (LIST (CAR MAIN_BLOCK_INSERTION_POINT) (+ (CADR MAIN_BLOCK_INSERTION_POINT) 100.00) 0.0) "1" "0")
      (COMMAND "INSERT" "TENSION_LENGTH" (LIST (CAR MAIN_BLOCK_INSERTION_POINT) (+ (CADR MAIN_BLOCK_INSERTION_POINT) 100.00) 0.0) "1" "0")
      (CHANGE_FLIP (ENTLAST) "TLF2")
      (INSERT_DYNAMIC_PROPERTIES (ENTLAST) '("TLM4 X") (LIST (+ (NTH 1 (NTH 0 (GET_DYNAMIC_PROPERTIES (ENTLAST) '("TLM4 X")))) 24.00)))
      (COMMAND "INSERT" "OLC" (LIST  (CAR MAIN_BLOCK_INSERTION_POINT)  (+ (CADR MAIN_BLOCK_INSERTION_POINT) 79.00) 0.0) "1" "0")
      (MODIFY_ATTRIBUTES (ENTLAST) (LIST "TRACK") (LIST "FOR DN MAIN"))
      (COMMAND "INSERT" "JUMPER" (LIST (- (CAR MAIN_BLOCK_INSERTION_POINT) 36.00) (- (CADR MAIN_BLOCK_INSERTION_POINT) 9.75) 0.0) "1" "0" )
      (INSERT_DYNAMIC_PROPERTIES (ENTLAST) '("Visibility1" "JUR1") (LIST "DOUBLE_LINE" (* 110 (/ PI 180))))
      (MODIFY_ATTRIBUTES (ENTLAST) (LIST "JUMPER_TYPE1") (LIST "G"))
      )
      )


    )
  )

  
 )
 )

;;;;;;;;;;;;;;;;;;;;;;;;;;

 (IF (= TRACK_TYPE "DN")
  (PROGN
  (IF (= INDENTIFICATION_STRING "BWA_END")
    (PROGN
      (COMMAND "INSERT" "ANCHOR" MAIN_BLOCK_INSERTION_POINT "1" "0" )
      (INSERT_DYNAMIC_PROPERTIES (ENTLAST) '("LENGTHEN") (LIST 4.00))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (COMMAND "INSERT" "TENSION_LENGTH" (LIST (CAR MAIN_BLOCK_INSERTION_POINT) (- (CADR MAIN_BLOCK_INSERTION_POINT) 48.25) 0.0) "1" "0" )
      (CHANGE_FLIP (ENTLAST) "TLF1")
      (INSERT_DYNAMIC_PROPERTIES (ENTLAST) '("TLM4 Y") (LIST (+ (NTH 1 (NTH 0 (GET_DYNAMIC_PROPERTIES (ENTLAST) '("TLM4 Y")))) 14.00)))
      (COMMAND "INSERT" "JUMPER" (LIST (- (CAR MAIN_BLOCK_INSERTION_POINT) 14.786) (+ (CADR MAIN_BLOCK_INSERTION_POINT) 3.2401) 0.0) "1" "0" )
      (INSERT_DYNAMIC_PROPERTIES (ENTLAST) '("Visibility1" "Angle1") (LIST "ATJ" (* 5 (/ PI 3))))
      (MODIFY_ATTRIBUTES (ENTLAST) (LIST "JUMPER_TYPE2") (LIST "3ATJ"))
    )
  )

  (IF (= INDENTIFICATION_STRING "BWA_START")
    (PROGN
      (COMMAND "INSERT" "ANCHOR" MAIN_BLOCK_INSERTION_POINT "1" "0" )
      (INSERT_DYNAMIC_PROPERTIES (ENTLAST) '("LENGTHEN") (LIST 4.00))
      (CHANGE_FLIP (ENTLAST) "ANF1")
      (INSERT_ATTRIBUTES (ENTLAST) '("WIRE_RUN1") (LIST (LIST (- (CAR MAIN_BLOCK_INSERTION_POINT) 16.00)  (- (CADR MAIN_BLOCK_INSERTION_POINT) 5.75) 0.0)))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (COMMAND "INSERT" "TENSION_LENGTH" (LIST (CAR MAIN_BLOCK_INSERTION_POINT) (- (CADR MAIN_BLOCK_INSERTION_POINT) 48.25) 0.0) "1" "0" )
      (CHANGE_FLIP (ENTLAST) "TLF1")
      (CHANGE_FLIP (ENTLAST) "TLF2")
      (INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      (COMMAND "INSERT" "JUMPER" (LIST (+ (CAR MAIN_BLOCK_INSERTION_POINT) 14.786) (+ (CADR MAIN_BLOCK_INSERTION_POINT) 3.2401) 0.0) "1" "0" )
      (INSERT_DYNAMIC_PROPERTIES (ENTLAST) '("Visibility1" "Angle1") (LIST "ATJ" (* 4 (/ PI 3))))
      (MODIFY_ATTRIBUTES (ENTLAST) (LIST "JUMPER_TYPE2") (LIST "3ATJ"))
    )
  )


  (IF (= INDENTIFICATION_STRING "ACA_END")
    (PROGN
      (COMMAND "INSERT" "ANCHOR" MAIN_BLOCK_INSERTION_POINT "1" "0" )
      (MODIFY_ATTRIBUTES (ENTLAST) (LIST "ANCHOR_TYPE1") (LIST "ACA"))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (INSERT_DYNAMIC_PROPERTIES (ENTLAST) '("LENGTHEN" "Visibility1") (LIST 4.00 "WITHOUT WEIGHTS"))
    )
  )


  (IF (= INDENTIFICATION_STRING "ACA_START")
    (PROGN
      (COMMAND "INSERT" "ANCHOR" MAIN_BLOCK_INSERTION_POINT "1" "0" )
      (INSERT_DYNAMIC_PROPERTIES (ENTLAST) '("LENGTHEN") (LIST 4.00))
      (CHANGE_FLIP (ENTLAST) "ANF1")
      (MODIFY_ATTRIBUTES (ENTLAST) (LIST "ANCHOR_TYPE1") (LIST "ACA"))
      (IF (/= WIRE_NUMBER1 NIL) (MODIFY_ATTRIBUTES (ENTLAST) (LIST "WIRE_RUN1") (LIST WIRE_NUMBER1)) (PROGN (MODIFY_ATTRIBUTES (ENTLAST) (LIST "WIRE_RUN1") (LIST (STRCAT "NA-" (RTOS NA 2 0)))) (SETQ NA (+ NA 1))))
      (INSERT_DYNAMIC_PROPERTIES (ENTLAST) '("LENGTHEN" "Visibility1") (LIST 4.00 "WITHOUT WEIGHTS"))
      (INSERT_ATTRIBUTES (ENTLAST) '("WIRE_RUN1") (LIST (LIST (- (CAR MAIN_BLOCK_INSERTION_POINT) 16.00)  (- (CADR MAIN_BLOCK_INSERTION_POINT) 5.75) 0.0)))
    )
  )



  (IF (= INDENTIFICATION_STRING "OLC")
    (PROGN
      (COMMAND "INSERT" "OLC" (LIST  (CAR MAIN_BLOCK_INSERTION_POINT)  (- (CADR MAIN_BLOCK_INSERTION_POINT) 23.50) 0.0) "1" "0" )
      (COMMAND "INSERT" "JUMPER" (LIST (+ (CAR MAIN_BLOCK_INSERTION_POINT) 36.00) (+ (CADR MAIN_BLOCK_INSERTION_POINT) 9.75) 0.0) "1" "0" )
      (INSERT_DYNAMIC_PROPERTIES (ENTLAST) '("Visibility1" "JUR1") (LIST "DOUBLE_LINE" (* 290 (/ PI 180))))
      (MODIFY_ATTRIBUTES (ENTLAST) (LIST "JUMPER_TYPE1") (LIST "G"))
    )
  )

  (IF (/= (VL-POSITION INDENTIFICATION_STRING (LIST "ACC" "ACCFA" "ACCAEWA")) NIL)
    (PROGN
    (IF (= INDENTIFICATION_STRING "ACC")
    (PROGN
      (COMMAND "INSERT" "ACC" (LIST  (CAR MAIN_BLOCK_INSERTION_POINT)  (- (CADR MAIN_BLOCK_INSERTION_POINT) 51.85) 0.0) "1" "0" )
      (INSERT_DYNAMIC_PROPERTIES (ENTLAST) '("ACF1") (LIST "1"))
      (INSERT_ATTRIBUTES (ENTLAST) '("MAST_COUNT1" "MAST_COUNT2" "ACC_NATURE") (LIST (LIST (- (CAR MAIN_BLOCK_INSERTION_POINT) 4.30)  (- (CADR MAIN_BLOCK_INSERTION_POINT) 49.85) 0.0) (LIST (+ (CAR MAIN_BLOCK_INSERTION_POINT) 2.00)  (- (CADR MAIN_BLOCK_INSERTION_POINT) 49.85) 0.0) (LIST (- (CAR MAIN_BLOCK_INSERTION_POINT) 10)  (- (CADR MAIN_BLOCK_INSERTION_POINT) 55.35) 0.0)))
      (MODIFY_ATTRIBUTES (ENTLAST) (LIST "ACC_NATURE") (LIST "ACC FOR UP MAIN"))
    )
    )
    (IF (= INDENTIFICATION_STRING "ACCFA")
      (PROGN
      (COMMAND "INSERT" "ACC" (LIST  (CAR MAIN_BLOCK_INSERTION_POINT)  (- (CADR MAIN_BLOCK_INSERTION_POINT) 61.85) 0.0) "1" "0" )
      (INSERT_DYNAMIC_PROPERTIES (ENTLAST) '("ACF1") (LIST "1"))
      (INSERT_ATTRIBUTES (ENTLAST) '("MAST_COUNT1" "MAST_COUNT2" "ACC_NATURE") (LIST (LIST (- (CAR MAIN_BLOCK_INSERTION_POINT) 4.30)  (- (CADR MAIN_BLOCK_INSERTION_POINT) 59.85) 0.0) (LIST (+ (CAR MAIN_BLOCK_INSERTION_POINT) 2.00)  (- (CADR MAIN_BLOCK_INSERTION_POINT) 59.85) 0.0) (LIST (- (CAR MAIN_BLOCK_INSERTION_POINT) 10)  (- (CADR MAIN_BLOCK_INSERTION_POINT) 63.85) 0.0)))
      (MODIFY_ATTRIBUTES (ENTLAST) (LIST "ACC_NATURE") (LIST "ACC FOR UP MAIN"))
      (COMMAND "INSERT" "BTB_ANC" MAIN_BLOCK_INSERTION_POINT "1" "0")
      (MODIFY_ATTRIBUTES (ENTLAST) (LIST "ANCHOR_TYPE1" "ANCHOR_TYPE2") (LIST "FA" "FA"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (INSERT_DYNAMIC_PROPERTIES (ENTLAST) '("Visibility1") (LIST "WITHOUT WEIGHTS"))
      (COMMAND "INSERT" "JUMPER" MAIN_BLOCK_INSERTION_POINT "1" "0")
      (INSERT_DYNAMIC_PROPERTIES (ENTLAST) '("Visibility1") (LIST "FJ/AEWA"))
      (MODIFY_ATTRIBUTES (ENTLAST) (LIST "JUMPER_TYPE1") (LIST "FJ"))
      (COMMAND "MIRROR" (ENTLAST) "" MAIN_BLOCK_INSERTION_POINT (LIST (+ (CAR MAIN_BLOCK_INSERTION_POINT) 10) (CADR MAIN_BLOCK_INSERTION_POINT) 0.0) "Y")
      (COMMAND "INSERT" "TENSION_LENGTH" (LIST (CAR MAIN_BLOCK_INSERTION_POINT) (- (CADR MAIN_BLOCK_INSERTION_POINT) 48.00) 0.0) "1" "0")
      (CHANGE_FLIP (ENTLAST) "TLF1")
      (INSERT_DYNAMIC_PROPERTIES (ENTLAST) '("TLM4 Y") (LIST (+ (NTH 1 (NTH 0 (GET_DYNAMIC_PROPERTIES (ENTLAST) '("TLM4 Y")))) 12.50)))
      (COMMAND "INSERT" "TENSION_LENGTH" (LIST (CAR MAIN_BLOCK_INSERTION_POINT) (- (CADR MAIN_BLOCK_INSERTION_POINT) 48.00) 0.0) "1" "0" )
      (CHANGE_FLIP (ENTLAST) "TLF1")
      (CHANGE_FLIP (ENTLAST) "TLF2")
      (INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      )
    )

      (IF (= INDENTIFICATION_STRING "ACCAEWA")
      (PROGN
      (COMMAND "INSERT" "ACC" (LIST  (CAR MAIN_BLOCK_INSERTION_POINT)  (- (CADR MAIN_BLOCK_INSERTION_POINT) 61.85) 0.0) "1" "0" )
      (INSERT_DYNAMIC_PROPERTIES (ENTLAST) '("ACF1") (LIST "1"))
      (INSERT_ATTRIBUTES (ENTLAST) '("MAST_COUNT1" "MAST_COUNT2" "ACC_NATURE") (LIST (LIST (- (CAR MAIN_BLOCK_INSERTION_POINT) 4.30)  (- (CADR MAIN_BLOCK_INSERTION_POINT) 59.85) 0.0) (LIST (+ (CAR MAIN_BLOCK_INSERTION_POINT) 2.00)  (- (CADR MAIN_BLOCK_INSERTION_POINT) 59.85) 0.0) (LIST (- (CAR MAIN_BLOCK_INSERTION_POINT) 10)  (- (CADR MAIN_BLOCK_INSERTION_POINT) 63.85) 0.0)))
      (MODIFY_ATTRIBUTES (ENTLAST) (LIST "ACC_NATURE") (LIST "ACC FOR UP MAIN"))
      (COMMAND "INSERT" "BTB_ANC" MAIN_BLOCK_INSERTION_POINT "1" "0")
      (MODIFY_ATTRIBUTES (ENTLAST) (LIST "ANCHOR_TYPE1" "ANCHOR_TYPE2") (LIST "AEWA" "AEWA"))
      (INSERT_DYNAMIC_PROPERTIES (ENTLAST) '("Visibility1") (LIST "WITHOUT WEIGHTS"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (COMMAND "INSERT" "JUMPER" MAIN_BLOCK_INSERTION_POINT "1" "0")
      (INSERT_DYNAMIC_PROPERTIES (ENTLAST) '("Visibility1") (LIST "FJ/AEWA"))
      (MODIFY_ATTRIBUTES (ENTLAST) (LIST "JUMPER_TYPE1") (LIST "AEWJ"))
      (COMMAND "MIRROR" (ENTLAST) "" MAIN_BLOCK_INSERTION_POINT (LIST (+ (CAR MAIN_BLOCK_INSERTION_POINT) 10) (CADR MAIN_BLOCK_INSERTION_POINT) 0.0) "Y")
      (COMMAND "INSERT" "TENSION_LENGTH" (LIST (CAR MAIN_BLOCK_INSERTION_POINT) (- (CADR MAIN_BLOCK_INSERTION_POINT) 48.00) 0.0) "1" "0")
      (CHANGE_FLIP (ENTLAST) "TLF1")
      (INSERT_DYNAMIC_PROPERTIES (ENTLAST) '("TLM4 Y") (LIST (+ (NTH 1 (NTH 0 (GET_DYNAMIC_PROPERTIES (ENTLAST) '("TLM4 Y")))) 12.50)))
      (COMMAND "INSERT" "TENSION_LENGTH" (LIST (CAR MAIN_BLOCK_INSERTION_POINT) (- (CADR MAIN_BLOCK_INSERTION_POINT) 48.00) 0.0) "1" "0" )
      (CHANGE_FLIP (ENTLAST) "TLF1")
      (CHANGE_FLIP (ENTLAST) "TLF2")
      (INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      
      )
      )
      (COMMAND "INSERT" "JUMPER" (LIST (+ (CAR MAIN_BLOCK_INSERTION_POINT) 4.20) (+ (CADR MAIN_BLOCK_INSERTION_POINT) 11.70) 0.0) "1" "0" )
      (INSERT_DYNAMIC_PROPERTIES (ENTLAST) '("Visibility1" "JUR1") (LIST "SINGLE_LINE" (* 60 (/ PI 180))))
      (MODIFY_ATTRIBUTES (ENTLAST) (LIST "JUMPER_TYPE1") (LIST "H"))
    )
     
  )
 

  (IF (/= (VL-POSITION INDENTIFICATION_STRING (LIST "AEWA" "DAEWA" "OLCAEWA")) NIL)
    (PROGN
      (COMMAND "INSERT" "BTB_ANC" MAIN_BLOCK_INSERTION_POINT "1" "0")
      (MODIFY_ATTRIBUTES (ENTLAST) (LIST "ANCHOR_TYPE1" "ANCHOR_TYPE2") (LIST "AEWA" "AEWA"))
      (INSERT_DYNAMIC_PROPERTIES (ENTLAST) '("Visibility1") (LIST "WITHOUT WEIGHTS"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (COMMAND "INSERT" "JUMPER" MAIN_BLOCK_INSERTION_POINT "1" "0")
      (INSERT_DYNAMIC_PROPERTIES (ENTLAST) '("Visibility1") (LIST "FJ/AEWA"))
      (MODIFY_ATTRIBUTES (ENTLAST) (LIST "JUMPER_TYPE1") (LIST "AEWJ"))
      (COMMAND "MIRROR" (ENTLAST) "" MAIN_BLOCK_INSERTION_POINT (LIST (+ (CAR MAIN_BLOCK_INSERTION_POINT) 10) (CADR MAIN_BLOCK_INSERTION_POINT) 0.0) "Y")
      (IF (/= (VL-POSITION INDENTIFICATION_STRING (LIST "AEWA" "DAEWA")) NIL)
      (PROGN
      (COMMAND "INSERT" "TENSION_LENGTH" (LIST (CAR MAIN_BLOCK_INSERTION_POINT) (- (CADR MAIN_BLOCK_INSERTION_POINT) 48.00) 0.0) "1" "0")
      (CHANGE_FLIP (ENTLAST) "TLF1")
      (INSERT_DYNAMIC_PROPERTIES (ENTLAST) '("TLM4 Y") (LIST (+ (NTH 1 (NTH 0 (GET_DYNAMIC_PROPERTIES (ENTLAST) '("TLM4 Y")))) 12.50)))
      (COMMAND "INSERT" "TENSION_LENGTH" (LIST (CAR MAIN_BLOCK_INSERTION_POINT) (- (CADR MAIN_BLOCK_INSERTION_POINT) 48.00) 0.0) "1" "0" )
      (CHANGE_FLIP (ENTLAST) "TLF1")
      (CHANGE_FLIP (ENTLAST) "TLF2")
      (INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      )
      (PROGN
      (COMMAND "INSERT" "TENSION_LENGTH" (LIST (CAR MAIN_BLOCK_INSERTION_POINT) (- (CADR MAIN_BLOCK_INSERTION_POINT) 68.00) 0.0) "1" "0")
      (CHANGE_FLIP (ENTLAST) "TLF1")
      (INSERT_DYNAMIC_PROPERTIES (ENTLAST) '("TLM4 Y") (LIST (+ (NTH 1 (NTH 0 (GET_DYNAMIC_PROPERTIES (ENTLAST) '("TLM4 Y")))) 12.50)))
      (COMMAND "INSERT" "TENSION_LENGTH" (LIST (CAR MAIN_BLOCK_INSERTION_POINT) (- (CADR MAIN_BLOCK_INSERTION_POINT) 68.00) 0.0) "1" "0" )
      (CHANGE_FLIP (ENTLAST) "TLF1")
      (CHANGE_FLIP (ENTLAST) "TLF2")
      (INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      (COMMAND "INSERT" "OLC" (LIST  (CAR MAIN_BLOCK_INSERTION_POINT)  (- (CADR MAIN_BLOCK_INSERTION_POINT) 10.00) 0.0) "1" "0" )
      (COMMAND "INSERT" "JUMPER" (LIST (+ (CAR MAIN_BLOCK_INSERTION_POINT) 36.00) (+ (CADR MAIN_BLOCK_INSERTION_POINT) 9.75) 0.0) "1" "0" )
      (INSERT_DYNAMIC_PROPERTIES (ENTLAST) '("Visibility1" "JUR1") (LIST "DOUBLE_LINE" (* 290 (/ PI 180))))
      (MODIFY_ATTRIBUTES (ENTLAST) (LIST "JUMPER_TYPE1") (LIST "G"))
      )
      )

    )
  )


 (IF (/= (VL-POSITION INDENTIFICATION_STRING (LIST "FA" "DFA" "OLCFA")) NIL)
    (PROGN
      (COMMAND "INSERT" "BTB_ANC" MAIN_BLOCK_INSERTION_POINT "1" "0")
      (MODIFY_ATTRIBUTES (ENTLAST) (LIST "ANCHOR_TYPE1" "ANCHOR_TYPE2") (LIST "FA" "FA"))
      (IF (/= WIRE_NUMBER1 NIL) (MODIFY_ATTRIBUTES (ENTLAST) (LIST "WIRE_NO1") (LIST WIRE_NUMBER1)) (PROGN (MODIFY_ATTRIBUTES (ENTLAST) (LIST "WIRE_NO1") (LIST (STRCAT "NA-" (RTOS NA 2 0)))) (SETQ NA (+ NA 1))))
      (IF (/= WIRE_NUMBER2 NIL) (MODIFY_ATTRIBUTES (ENTLAST) (LIST "WIRE_NO2") (LIST WIRE_NUMBER2)) (PROGN (MODIFY_ATTRIBUTES (ENTLAST) (LIST "WIRE_NO2") (LIST (STRCAT "NA-" (RTOS NA 2 0)))) (SETQ NA (+ NA 1))))
      (INSERT_DYNAMIC_PROPERTIES (ENTLAST) '("Visibility1") (LIST "WITHOUT WEIGHTS"))
      (COMMAND "INSERT" "JUMPER" MAIN_BLOCK_INSERTION_POINT "1" "0")
      (INSERT_DYNAMIC_PROPERTIES (ENTLAST) '("Visibility1") (LIST "FJ/AEWA"))
      (MODIFY_ATTRIBUTES (ENTLAST) (LIST "JUMPER_TYPE1") (LIST "FJ"))
      (COMMAND "MIRROR" (ENTLAST) "" MAIN_BLOCK_INSERTION_POINT (LIST (+ (CAR MAIN_BLOCK_INSERTION_POINT) 10) (CADR MAIN_BLOCK_INSERTION_POINT) 0.0) "Y")
      (IF (/= (VL-POSITION INDENTIFICATION_STRING (LIST "FA" "DFA")) NIL)
      (PROGN
      (COMMAND "INSERT" "TENSION_LENGTH" (LIST (CAR MAIN_BLOCK_INSERTION_POINT) (- (CADR MAIN_BLOCK_INSERTION_POINT) 48.00) 0.0) "1" "0")
      (CHANGE_FLIP (ENTLAST) "TLF1")
      (INSERT_DYNAMIC_PROPERTIES (ENTLAST) '("TLM4 Y") (LIST (+ (NTH 1 (NTH 0 (GET_DYNAMIC_PROPERTIES (ENTLAST) '("TLM4 Y")))) 12.50)))
      (COMMAND "INSERT" "TENSION_LENGTH" (LIST (CAR MAIN_BLOCK_INSERTION_POINT) (- (CADR MAIN_BLOCK_INSERTION_POINT) 48.00) 0.0) "1" "0" )
      (CHANGE_FLIP (ENTLAST) "TLF1")
      (CHANGE_FLIP (ENTLAST) "TLF2")
      (INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      )
      (PROGN
      (COMMAND "INSERT" "TENSION_LENGTH" (LIST (CAR MAIN_BLOCK_INSERTION_POINT) (- (CADR MAIN_BLOCK_INSERTION_POINT) 68.00) 0.0) "1" "0")
      (CHANGE_FLIP (ENTLAST) "TLF1")
      (INSERT_DYNAMIC_PROPERTIES (ENTLAST) '("TLM4 Y") (LIST (+ (NTH 1 (NTH 0 (GET_DYNAMIC_PROPERTIES (ENTLAST) '("TLM4 Y")))) 12.50)))
      (COMMAND "INSERT" "TENSION_LENGTH" (LIST (CAR MAIN_BLOCK_INSERTION_POINT) (- (CADR MAIN_BLOCK_INSERTION_POINT) 68.00) 0.0) "1" "0" )
      (CHANGE_FLIP (ENTLAST) "TLF1")
      (CHANGE_FLIP (ENTLAST) "TLF2")
      (INSERT_DYNAMIC_PROPERTIES (ENTLAST) '("TLM4 X" "TLM4 Y") (LIST (+ (NTH 1 (NTH 0 (GET_DYNAMIC_PROPERTIES (ENTLAST) '("TLM4 X")))) 24.00) (+ (NTH 1 (NTH 0 (GET_DYNAMIC_PROPERTIES (ENTLAST) '("TLM4 Y")))) 12.50)))
      (COMMAND "INSERT" "OLC" (LIST  (CAR MAIN_BLOCK_INSERTION_POINT)  (- (CADR MAIN_BLOCK_INSERTION_POINT) 10.00) 0.0) "1" "0" )
      (COMMAND "INSERT" "JUMPER" (LIST (+ (CAR MAIN_BLOCK_INSERTION_POINT) 36.00) (+ (CADR MAIN_BLOCK_INSERTION_POINT) 9.75) 0.0) "1" "0" )
      (INSERT_DYNAMIC_PROPERTIES (ENTLAST) '("Visibility1" "JUR1") (LIST "DOUBLE_LINE" (* 290 (/ PI 180))))
      (MODIFY_ATTRIBUTES (ENTLAST) (LIST "JUMPER_TYPE1") (LIST "G"))
      )
      )

    )
  )
 )
  
 )
)














(DEFUN WIRE_NUMBERING ( LOCATION_LIST TRACK_TYPE / I TEMP_LIST BWA_LIST ACA_LIST AEWA_LIST FA_LIST )
  (SETQ I 0 TEMP_LIST NIL)
  (WHILE (< I (LENGTH LOCATION_LIST))
    (SETQ TEMP_LIST (CONS (LIST I (NTH I LOCATION_LIST)) TEMP_LIST))
    (SETQ I (+ I 1))
  )
  (SETQ TEMP_LIST (REVERSE TEMP_LIST))
  (SETQ BWA_LIST (BWA_NUMBERING (SORT_FUN (FILTER_LIST (LIST "BWA_START" "BWA_END") TEMP_LIST 1) 0 0) TRACK_TYPE))
  (SETQ ACA_LIST (ACA_NUMBERING (SORT_FUN (FILTER_LIST (LIST "ACA_START" "ACA_END") TEMP_LIST 1) 0 0) TRACK_TYPE))
  (SETQ AEWA_LIST (AEWA/FA_NUMBERING (SORT_FUN (FILTER_LIST (LIST "AEWA" "OLCAEWA" "DAEWA" "ACCAEWA") TEMP_LIST 1) 0 0) "AE" TRACK_TYPE))
  (SETQ FA_LIST (AEWA/FA_NUMBERING (SORT_FUN (FILTER_LIST (LIST "FA" "OLCFA" "DFA" "ACCFA") TEMP_LIST 1) 0 0) "FA" TRACK_TYPE))
  (SORT_FUN (MERGE_ANCHOR_LIST TEMP_LIST (APPEND BWA_LIST ACA_LIST AEWA_LIST FA_LIST)) 0 0)
)


(DEFUN BWA_NUMBERING ( BWA_LIST TRACK_TYPE / BWA_NUMBERING1 BWA_START_LIST BWA_END_LIST I START_TEMP_LIST END_TEMP_LIST)
  (IF (= (NTH 1 (NTH 0 BWA_LIST)) "BWA_END") (SETQ BWA_NUMBERING1 (CDR BWA_LIST)) (SETQ BWA_NUMBERING1 BWA_LIST))
  (SETQ BWA_START_LIST (SORT_FUN (FILTER_LIST (LIST "BWA_START") BWA_NUMBERING1 1) 2 0))
  (SETQ BWA_END_LIST (CDR (SORT_FUN (FILTER_LIST (LIST "BWA_END") BWA_NUMBERING1 1) 2 0)))
  (SETQ I 0 START_TEMP_LIST NIL END_TEMP_LIST NIL)
  (IF (= TRACK_TYPE "UP") (SETQ J 2) (SETQ J 1))
  (IF (AND (/= BWA_START_LIST NIL) (/= BWA_END_LIST NIL))
  (PROGN
  (WHILE (< I (LENGTH BWA_START_LIST))
    (SETQ START_TEMP_LIST (CONS (APPEND (NTH I BWA_START_LIST) (LIST (STRCAT "W-" (RTOS J 2 0)))) START_TEMP_LIST))
    (IF (/= (NTH I BWA_END_LIST) NIL)
    (SETQ END_TEMP_LIST (CONS (APPEND (NTH I BWA_END_LIST) (LIST (STRCAT "W-" (RTOS J 2 0)))) END_TEMP_LIST))
    )
    (SETQ I (+ I 1))
    (SETQ J (+ J 2))
  )
  )
  )
(APPEND START_TEMP_LIST END_TEMP_LIST)
)


(DEFUN ACA_NUMBERING ( ACA_LIST TRACK_TYPE / ACA_NUMBERING1 ACA_START_LIST ACA_END_LIST I START_TEMP_LIST END_TEMP_LIST)
  (IF (= (NTH 1 (NTH 0 ACA_LIST)) "ACA_END") (SETQ ACA_NUMBERING1 (CDR ACA_LIST)) (SETQ ACA_NUMBERING1 ACA_LIST))
  (SETQ ACA_START_LIST (SORT_FUN (FILTER_LIST (LIST "ACA_START") ACA_NUMBERING1 1) 0 0))
  (SETQ ACA_END_LIST (SORT_FUN (FILTER_LIST (LIST "ACA_END") ACA_NUMBERING1 1) 0 0))
  (SETQ I 0)
  (IF (= TRACK_TYPE "UP") (SETQ J 2) (SETQ J 1))
  (WHILE (< I (LENGTH ACA_START_LIST))
    (SETQ START_TEMP_LIST (CONS (APPEND (NTH I ACA_START_LIST) (LIST (STRCAT "AC-" (RTOS J 2 0)))) START_TEMP_LIST))
    (IF (/= (NTH I ACA_END_LIST) NIL)
    (SETQ END_TEMP_LIST (CONS (APPEND (NTH I ACA_END_LIST) (LIST (STRCAT "AC-" (RTOS J 2 0)))) END_TEMP_LIST))
    )
    (SETQ I (+ I 1))
    (SETQ J (+ J 2))
  )
(APPEND START_TEMP_LIST END_TEMP_LIST)
)




(DEFUN AEWA/FA_NUMBERING ( ANCHOR_LIST STRING TRACK_TYPE / I J K TEMP_LIST)
(SETQ I 0 TEMP_LIST NIL)
(IF (= TRACK_TYPE "UP") (SETQ J 0 K 2) (SETQ J -1 K 1))
  (WHILE (< I (LENGTH ANCHOR_LIST))
    (IF (/= I 0)
      (SETQ TEMP_LIST (CONS (APPEND (NTH I ANCHOR_LIST) (LIST (STRCAT STRING "-" (RTOS J 2 0)) (STRCAT STRING "-" (RTOS K 2 0)))) TEMP_LIST))
      (SETQ TEMP_LIST (CONS (APPEND (NTH I ANCHOR_LIST) (LIST "NA-0" (STRCAT STRING "-" (RTOS K 2 0)))) TEMP_LIST))
    )
    (SETQ I (+ I 1))
    (SETQ J (+ J 2))
    (SETQ K (+ K 2))
  )
(REVERSE TEMP_LIST)
)



(DEFUN MERGE_ANCHOR_LIST (MAIN_LIST LIST_TO_MERGE / I TEMP_ELE)
  (SETQ I 0 TEMP_ELE NIL)
  (WHILE (< I (LENGTH LIST_TO_MERGE))
    (SETQ TEMP_ELE (NTH I LIST_TO_MERGE))
    (SETQ MAIN_LIST (APPEND (VL-REMOVE (ASSOC (NTH 0 TEMP_ELE) MAIN_LIST) MAIN_LIST) (LIST TEMP_ELE)))
    (SETQ I (+ I 1))
  )
(REVERSE MAIN_LIST)
)






(DEFUN SORT_MULTILEVEL	(LIST1 FLAG1 FLAG2 FLAG3 /)
  (IF (= NIL (VL-CONSP (CAR LIST1)))
    (PROGN (SETQ LIST1 (INDEX_ADD LIST1))
	   (SETQ LIST1
		  (VL-SORT LIST1
			   '(LAMBDA (X Y) (< (CADR X) (CADR Y)))
		  )
	   )
	   (SETQ LIST1 (MAPCAR '(LAMBDA (X) (CADR X)) LIST1))
    )
    (PROGN
      (IF (NOT (ATOM (NTH FLAG1 (NTH 0 LIST1))))
	(SETQ LIST1
	       (VL-SORT
		 LIST1
		 '(LAMBDA (X Y)
		    (IF (/= (ATOF (RTOS (NTH FLAG2 (NTH FLAG1 X)) 2 1)) (ATOF (RTOS (NTH FLAG2 (NTH FLAG1 Y)) 2 1))) (< (ATOF (RTOS (NTH FLAG2 (NTH FLAG1 X)) 2 2)) (ATOF (RTOS (NTH FLAG2 (NTH FLAG1 Y)) 2 2))) (< (ATOF (RTOS (NTH FLAG3 (NTH FLAG1 X)) 2 2)) (ATOF (RTOS (NTH FLAG3 (NTH FLAG1 Y)) 2 2))))
		  )
	       )
	)
	(PROGN (SETQ LIST1
		      (VL-SORT LIST1
			       '(LAMBDA (X Y) (IF (/= (ATOF (RTOS (NTH FLAG2 X) 2 2)) (ATOF (RTOS (NTH FLAG2 Y) 2 2))) (< (ATOF (RTOS (NTH FLAG2 X) 2 2)) (ATOF (RTOS (NTH FLAG2 Y) 2 2))) (< (ATOF (RTOS (NTH FLAG3 X) 2 2)) (ATOF (RTOS (NTH FLAG3 Y) 2 2))))) 
		      )
	       )
	)
      )
    )
  )
  LIST1
)



(DEFUN ASSIGN_LOCATION_NUMBERS (MAST_LIST / COUNTER TEMP_ELE FINAL_LIST I )
    (SETQ COUNTER 1 TEMP_ELE NIL FINAL_LIST NIL)
    (SETQ I 0)
  (WHILE (< I (LENGTH MAST_LIST))
    (IF (= (NTH 2 (NTH I MAST_LIST)) "UP")
      (PROGN
	(IF (= (REM COUNTER 2) 0) (SETQ COUNTER (+ COUNTER 1)))
	(SETQ TEMP_ELE (APPEND (NTH I MAST_LIST) (LIST (RTOS COUNTER 2 0))))
      )
      (PROGN
	(IF (= (REM COUNTER 2) 1) (SETQ COUNTER (+ COUNTER 1)))
	(SETQ TEMP_ELE (APPEND (NTH I MAST_LIST) (LIST (RTOS COUNTER 2 0))))
      )
    )(SETQ FINAL_LIST (CONS TEMP_ELE FINAL_LIST))
  (SETQ COUNTER (+ COUNTER 1))
  (SETQ I (+ I 1))
 )
(REVERSE FINAL_LIST)
)

(DEFUN C:DRAW_PEGGINGPLAN ( / )
  (SETQ WPT1 (GETPOINT "ENTER STARTING POINT IN LOP"))
  (SETQ WPT2 (GETPOINT "\n ENTER ENDING POINT IN LOP"))
  (SETQ BLOCKS_LIST (FORM_SSSET (SSGET "W" WPT1 WPT2 (LIST (CONS 0 "INSERT")))))
  (SETQ BLOCK_NAME_LIST (EXTRACT_ENTITY_INFO2 BLOCKS_LIST))
  (SETQ KM_STONE_LIST (FILTER_LIST (LIST "KM_NEW" "KM_STONE" "KMNEW" "KMSTONE") BLOCK_NAME_LIST 1))
  (SETQ KM_STONE_LIST (SORT_FUN (ENTITY_DFX (SINGLE_ELE_LIST KM_STONE_LIST 0) 10 -1) 1 0))
  (SETQ KM_STONE_COORDINATES (GET_KM_STONE_COORDINATES KM_STONE_LIST))
  (SETQ SCALE (GETREAL "\nENTER SCALE : "))
  (PROMPT "SELECT OFFSETS (OFFSET COLOUR CODE : GREEN->SINGLE CANTILEVER YELLOW->DOUBLE CANTILEVER")
  (SETQ OFFSET_ENTITIES1 (SSGET))
  (SETQ OFFSET_ENTITIES2 (SSGET))
  (PROMPT "\nSELECT TRACK ALIGNMENT FOR UP TRACK:")
  (SETQ TRACK_ENTITY_UPTRACK (FORM_SSSET(SSGET)))
  (PROMPT "\nSELECT TRACK ALIGNMENT FOR DN TRACK:")
  (SETQ TRACK_ENTITY_DNTRACK (FORM_SSSET(SSGET)))
  (SETQ ENTNAME_UPTRACK (CAR(ENTSEL "\nSELECT REFERENCE MAST FOR UP TRACK:")))
  (SETQ ENTNAME_DNTRACK (CAR(ENTSEL "\nSELECT REFERENCE MAST FOR DN TRACK:")))
  (SETQ UPLINE_MASTS (INSERT_MASTS_NORMAL OFFSET_ENTITIES1 TRACK_ENTITY_UPTRACK SCALE ENTNAME_UPTRACK))
  (SETQ DNLINE_MASTS (INSERT_MASTS_DN_NORMAL OFFSET_ENTITIES2 TRACK_ENTITY_DNTRACK SCALE ENTNAME_DNTRACK))
  
  (SETQ UPLINE_MAST_ENTITIES (ADD_LISTS (EXTRACT_ENTITY_INFO (SINGLE_ELE_LIST UPLINE_MASTS 0) 1 3) (N_ELE_LIST "DN" (LENGTH UPLINE_MASTS))))
  (SETQ DNLINE_MAST_ENTITIES (ADD_LISTS (EXTRACT_ENTITY_INFO (SINGLE_ELE_LIST DNLINE_MASTS 0) 1 3) (N_ELE_LIST "UP" (LENGTH DNLINE_MASTS))))
  
  (SETQ UPLINE_MASTS (FIND_IN_BETWEEN (SINGLE_ELE_LIST KM_STONE_COORDINATES 1) UPLINE_MAST_ENTITIES 0 0 1))
  (SETQ DNLINE_MASTS (FIND_IN_BETWEEN (SINGLE_ELE_LIST KM_STONE_COORDINATES 1) DNLINE_MAST_ENTITIES 0 0 1))
  (UPDATE_TOTAL_CHAINAGES_SPLIT (VL-REMOVE (NTH (- (LENGTH KM_STONE_COORDINATES) 1) KM_STONE_COORDINATES) KM_STONE_COORDINATES) UPLINE_MASTS DNLINE_MASTS SCALE ENTNAME_UPTRACK ENTNAME_DNTRACK)
)

(DEFUN C:UPDATE_TOTAL_CHAINAGES ( / )
  (SETQ WPT1 (GETPOINT "ENTER STARTING POINT IN LOP"))
  (SETQ WPT2 (GETPOINT "\n ENTER ENDING POINT IN LOP"))
  (SETQ BLOCKS_LIST (FORM_SSSET (SSGET "W" WPT1 WPT2 (LIST (CONS 0 "INSERT")))))
  (SETQ MAST_ENTITIES (YARD_DATA_COLLECT WPT1 WPT2 '("SINGLE_CANT_MAST" "DOUBLE_CANT_MAST" "TRIPLE_CANT_MAST" "TTC" "SS1" "SS2" "SS3" "SS4") 1 5))
  (SETQ BLOCK_NAME_LIST (EXTRACT_ENTITY_INFO2 BLOCKS_LIST))
  (SETQ KM_STONE_LIST (FILTER_LIST (LIST "KM_NEW" "KM_STONE" "KMNEW" "KMSTONE") BLOCK_NAME_LIST 1))
  (SETQ KM_STONE_LIST (SORT_FUN (ENTITY_DFX (SINGLE_ELE_LIST KM_STONE_LIST 0) 10 -1) 1 0))
  (SETQ KM_STONE_COORDINATES (GET_KM_STONE_COORDINATES KM_STONE_LIST))
  (SETQ SCALE (GETREAL "\nENTER SCALE : "))
  ;(PROMPT "SELECT OFFSETS (OFFSET COLOUR CODE : GREEN->SINGLE CANTILEVER YELLOW->DOUBLE CANTILEVER")
  ;(SETQ OFFSET_ENTITIES1 (SSGET))
  ;(SETQ TRACK_ENTITY_UPTRACK (CAR(ENTSEL "\nSELECT TRACK ALIGNMENT FOR UP TRACK:")))
  ;(SETQ TRACK_ENTITY_DNTRACK (CAR(ENTSEL "\nSELECT TRACK ALIGNMENT FOR DN TRACK:")))
  (SETQ ENTNAME_UPTRACK (CAR(ENTSEL "\nSELECT REFERENCE MAST FOR UP TRACK:")))
  (SETQ ENTNAME_DNTRACK (CAR(ENTSEL "\nSELECT REFERENCE MAST FOR DN TRACK:")))
  (SETQ UPLINE_MAST_ENTITIES (FILTER_LIST '("DN") MAST_ENTITIES 1))
  (SETQ DNLINE_MAST_ENTITIES (FILTER_LIST '("UP") MAST_ENTITIES 1))
  (SETQ UPLINE_MAST_ENTITIES (ADD_LISTS (EXTRACT_ENTITY_INFO (SINGLE_ELE_LIST UPLINE_MAST_ENTITIES 0) 1 3) (N_ELE_LIST "DN" (LENGTH UPLINE_MAST_ENTITIES))))
  (SETQ DNLINE_MAST_ENTITIES (ADD_LISTS (EXTRACT_ENTITY_INFO (SINGLE_ELE_LIST DNLINE_MAST_ENTITIES 0) 1 3) (N_ELE_LIST "UP" (LENGTH DNLINE_MAST_ENTITIES))))
  (SETQ UPLINE_MASTS (FIND_IN_BETWEEN (SINGLE_ELE_LIST KM_STONE_COORDINATES 1) UPLINE_MAST_ENTITIES 0 0 1))
  (SETQ DNLINE_MASTS (FIND_IN_BETWEEN (SINGLE_ELE_LIST KM_STONE_COORDINATES 1) DNLINE_MAST_ENTITIES 0 0 1))
  ;(UPDATE_TOTAL_CHAINAGES (VL-REMOVE (NTH (- (LENGTH KM_STONE_COORDINATES) 1) KM_STONE_COORDINATES) KM_STONE_COORDINATES) UPLINE_MASTS SCALE "02" ENTNAME_UPTRACK)
  ;(UPDATE_TOTAL_CHAINAGES (VL-REMOVE (NTH (- (LENGTH KM_STONE_COORDINATES) 1) KM_STONE_COORDINATES) KM_STONE_COORDINATES) DNLINE_MASTS SCALE "01" ENTNAME_DNTRACK)

  (UPDATE_TOTAL_CHAINAGES_SPLIT (VL-REMOVE (NTH (- (LENGTH KM_STONE_COORDINATES) 1) KM_STONE_COORDINATES) KM_STONE_COORDINATES) UPLINE_MASTS DNLINE_MASTS SCALE ENTNAME_UPTRACK ENTNAME_DNTRACK)
)




(DEFUN C:UPDATE_TOTAL_CHAINAGES_QUICK ( / )
  (SETQ WPT1 (GETPOINT "ENTER STARTING POINT IN LOP"))
  (SETQ WPT2 (GETPOINT "\n ENTER ENDING POINT IN LOP"))
  (SETQ BLOCKS_LIST (FORM_SSSET (SSGET "W" WPT1 WPT2 (LIST (CONS 0 "INSERT")))))
  (SETQ MAST_ENTITIES (YARD_DATA_COLLECT WPT1 WPT2 '("SINGLE_CANT_MAST" "DOUBLE_CANT_MAST" "TRIPLE_CANT_MAST" "TTC" "SS1" "SS2" "SS3" "SS4") 1 5))
  (SETQ BLOCK_NAME_LIST (EXTRACT_ENTITY_INFO2 BLOCKS_LIST))
  (SETQ KM_STONE_LIST (FILTER_LIST (LIST "KM_NEW" "KM_STONE" "KMNEW" "KMSTONE") BLOCK_NAME_LIST 1))
  (SETQ KM_STONE_LIST (SORT_FUN (ENTITY_DFX (SINGLE_ELE_LIST KM_STONE_LIST 0) 10 -1) 1 0))
  (SETQ KM_STONE_COORDINATES (GET_KM_STONE_COORDINATES KM_STONE_LIST))
  (SETQ SCALE (GETREAL "\nENTER SCALE : "))
  ;(PROMPT "SELECT OFFSETS (OFFSET COLOUR CODE : GREEN->SINGLE CANTILEVER YELLOW->DOUBLE CANTILEVER")
  ;(SETQ OFFSET_ENTITIES1 (SSGET))
  ;(SETQ TRACK_ENTITY_UPTRACK (CAR(ENTSEL "\nSELECT TRACK ALIGNMENT FOR UP TRACK:")))
  ;(SETQ TRACK_ENTITY_DNTRACK (CAR(ENTSEL "\nSELECT TRACK ALIGNMENT FOR DN TRACK:")))
  (SETQ ENTNAME_UPTRACK (CAR(ENTSEL "\nSELECT REFERENCE MAST FOR UP TRACK:")))
  (SETQ ENTNAME_DNTRACK (CAR(ENTSEL "\nSELECT REFERENCE MAST FOR DN TRACK:")))
  (SETQ UPLINE_MAST_ENTITIES (FILTER_LIST '("DN") MAST_ENTITIES 1))
  (SETQ DNLINE_MAST_ENTITIES (FILTER_LIST '("UP") MAST_ENTITIES 1))
  (SETQ UPLINE_MAST_ENTITIES (ADD_LISTS (EXTRACT_ENTITY_INFO (SINGLE_ELE_LIST UPLINE_MAST_ENTITIES 0) 1 3) (N_ELE_LIST "DN" (LENGTH UPLINE_MAST_ENTITIES))))
  (SETQ DNLINE_MAST_ENTITIES (ADD_LISTS (EXTRACT_ENTITY_INFO (SINGLE_ELE_LIST DNLINE_MAST_ENTITIES 0) 1 3) (N_ELE_LIST "UP" (LENGTH DNLINE_MAST_ENTITIES))))
  (SETQ UPLINE_MASTS (FIND_IN_BETWEEN (SINGLE_ELE_LIST KM_STONE_COORDINATES 1) UPLINE_MAST_ENTITIES 0 0 1))
  (SETQ DNLINE_MASTS (FIND_IN_BETWEEN (SINGLE_ELE_LIST KM_STONE_COORDINATES 1) DNLINE_MAST_ENTITIES 0 0 1))
  ;(UPDATE_TOTAL_CHAINAGES (VL-REMOVE (NTH (- (LENGTH KM_STONE_COORDINATES) 1) KM_STONE_COORDINATES) KM_STONE_COORDINATES) UPLINE_MASTS SCALE "02" ENTNAME_UPTRACK)
  ;(UPDATE_TOTAL_CHAINAGES (VL-REMOVE (NTH (- (LENGTH KM_STONE_COORDINATES) 1) KM_STONE_COORDINATES) KM_STONE_COORDINATES) DNLINE_MASTS SCALE "01" ENTNAME_DNTRACK)

  (UPDATE_TOTAL_CHAINAGES_SPLIT2 (VL-REMOVE (NTH (- (LENGTH KM_STONE_COORDINATES) 1) KM_STONE_COORDINATES) KM_STONE_COORDINATES) UPLINE_MASTS DNLINE_MASTS SCALE ENTNAME_UPTRACK ENTNAME_DNTRACK)
)





(DEFUN UPDATE_TOTAL_CHAINAGES_SPLIT (KM_LIST UPLIST DNLIST SCALE ENTNAME_UPTRACK ENTNAME_DNTRACK / I F LOC_NO ST_CH ENT_LIST )
     (SETQ F 0 TEMP_ELE1 NIL TEMP_ELE2 NIL )
   (setq dcl_id (load_dialog "DISPLAY_INFO.dcl"))
   (new_dialog "DISPLAY_INFO" dcl_id)
  (WHILE (< F (LENGTH KM_LIST))
    (SETQ TEMP_ELE1 (NTH F KM_LIST) TEMP_ELE2 (NTH F UPLIST) TEMP_ELE3 (NTH F DNLIST))
     (SET_TILE "INFO" (STRCAT "UPDATING KM " (ITOA (+ F 1)) " OF "  (ITOA (LENGTH KM_LIST))))
     (SET_TILE "PERCENTAGE" (STRCAT (RTOS (/ (* (+ F 1) 100) (ATOF (RTOS (LENGTH KM_LIST) 2 2)) ) 2 2) "%" "COMPLETED"))
    (IF (= F (- (LENGTH KM_LIST) 1))
      (PROGN
      (SET_TILE "INFO" (STRCAT "ALL " "KILOMETER" " LOCATIONS ARE UPDATED SUCESSFULLY"))
      (SET_TILE "PERCENTAGE" "PRESS OK TO CONTINUE")
      )
    )
    ;(SETQ LOC_NO (STRCAT (NTH 0 TEMP_ELE1) "/" STARTING_LOCATION))
    (SETQ ST_CH_UP (STRCAT (NTH 0 TEMP_ELE1) "/" (RTOS (- (NTH 0 (NTH 1 (NTH 0 (SORT_FUN TEMP_ELE2 1 0)))) (NTH 0 (NTH 1 TEMP_ELE1))) 2 2)))
    (SETQ ST_CH_DN (STRCAT (NTH 0 TEMP_ELE1) "/" (RTOS (- (NTH 0 (NTH 1 (NTH 0 (SORT_FUN TEMP_ELE3 1 0)))) (NTH 0 (NTH 1 TEMP_ELE1))) 2 2)))
    (SETQ TEMP_MAIN_LIST (ASSIGN_LOCATION_NUMBERS (SORT_MULTILEVEL (APPEND TEMP_ELE2 TEMP_ELE3) 1 0 1)))
    (UPDATE_CHAINAGES_SPLIT SCALE ST_CH_UP (BUILD_LIST (FILTER_LIST (LIST "DN") TEMP_MAIN_LIST 2) (LIST 0 3)) ENTNAME_UPTRACK)
    (UPDATE_CHAINAGES_SPLIT SCALE ST_CH_DN (BUILD_LIST (FILTER_LIST (LIST "UP") TEMP_MAIN_LIST 2) (LIST 0 3)) ENTNAME_DNTRACK)
    (SETQ F (+ F 1))
  )
  (setq ddiag(start_dialog))
)




(DEFUN UPDATE_TOTAL_CHAINAGES_SPLIT2 (KM_LIST UPLIST DNLIST SCALE ENTNAME_UPTRACK ENTNAME_DNTRACK / I F LOC_NO ST_CH ENT_LIST )
     (SETQ F 0 TEMP_ELE1 NIL TEMP_ELE2 NIL )
   (setq dcl_id (load_dialog "DISPLAY_INFO.dcl"))
   (new_dialog "DISPLAY_INFO" dcl_id)
  (WHILE (< F (LENGTH KM_LIST))
    (SETQ TEMP_ELE1 (NTH F KM_LIST) TEMP_ELE2 (NTH F UPLIST) TEMP_ELE3 (NTH F DNLIST))
     (SET_TILE "INFO" (STRCAT "UPDATING KM " (ITOA (+ F 1)) " OF "  (ITOA (LENGTH KM_LIST))))
     (SET_TILE "PERCENTAGE" (STRCAT (RTOS (/ (* (+ F 1) 100) (ATOF (RTOS (LENGTH KM_LIST) 2 2)) ) 2 2) "%" "COMPLETED"))
    (IF (= F (- (LENGTH KM_LIST) 1))
      (PROGN
      (SET_TILE "INFO" (STRCAT "ALL " "KILOMETER" " LOCATIONS ARE UPDATED SUCESSFULLY"))
      (SET_TILE "PERCENTAGE" "PRESS OK TO CONTINUE")
      )
    )
    ;(SETQ LOC_NO (STRCAT (NTH 0 TEMP_ELE1) "/" STARTING_LOCATION))
    (SETQ ST_CH_UP (STRCAT (NTH 0 TEMP_ELE1) "/" (RTOS (- (NTH 0 (NTH 1 (NTH 0 (SORT_FUN TEMP_ELE2 1 0)))) (NTH 0 (NTH 1 TEMP_ELE1))) 2 2)))
    (SETQ ST_CH_DN (STRCAT (NTH 0 TEMP_ELE1) "/" (RTOS (- (NTH 0 (NTH 1 (NTH 0 (SORT_FUN TEMP_ELE3 1 0)))) (NTH 0 (NTH 1 TEMP_ELE1))) 2 2)))
    (SETQ TEMP_MAIN_LIST (ASSIGN_LOCATION_NUMBERS (SORT_MULTILEVEL (APPEND TEMP_ELE2 TEMP_ELE3) 1 0 1)))
    (UPDATE_CHAINAGES_SPLIT2 SCALE ST_CH_UP (BUILD_LIST (FILTER_LIST (LIST "DN") TEMP_MAIN_LIST 2) (LIST 0 3)) ENTNAME_UPTRACK)
    (UPDATE_CHAINAGES_SPLIT2 SCALE ST_CH_DN (BUILD_LIST (FILTER_LIST (LIST "UP") TEMP_MAIN_LIST 2) (LIST 0 3)) ENTNAME_DNTRACK)
    (SETQ F (+ F 1))
  )
  (setq ddiag(start_dialog))
)

(DEFUN UPDATE_CHAINAGES_SPLIT2 (SCALE ST_CH ENT_LIST REFERENCE_TRACK / SSSET LOC_NO ST_CH LOC_NUM_LIST ENT_LIST BS_PT BS_PT1 ENT_INFO VALUES VALUES1 VALUES2 VALUES3 VALUES4 FDN_REFERENCE FDN_REFERENCE_X FDN_REFERENCE_Y RD_REFERENCE RD_REFERENCE_X RD_REFERENCE_Y TC_REFERENCE TC_REFERENCE_X TC_REFERENCE_Y SPAN_REFERENCE_X SPAN_REFERENCE_Y ENT_LIST_SPAN POINT POINT1 POINT2 POINT3 ENT_LIST_SPAN VISIBILITY_SPAN VISIBILITY_TC VISIBILITY_FDN VISIBILITY_RD I LOC CH TEMP_ELE SCALE POINT_FDN POINT_RD POINT_TC TEMP_SPAN)
  ;(PROMPT "\n SELECT MASTS")
  ;(SETQ SSSET (SSGET))
  ;(SETQ SCALE (GETREAL "\n ENTER SCALE : "))
  ;(SETQ LOC_NO (GETSTRING "\n ENTER STARTING MAST LOCATION NUMBER :"))
  ;(SETQ ST_CH (GETSTRING "\n ENTER STARTING MAST CHAINAGE :"))
  (SETQ	KM_NO (SUBSTR ST_CH 1 (VL-STRING-POSITION (ASCII "/") ST_CH)))
  ;(SETQ	LOC_NO	(SUBSTR	LOC_NO (+ (VL-STRING-POSITION (ASCII "/") LOC_NO) 2)))
  (SETQ	ST_CH	(SUBSTR	ST_CH (+ (VL-STRING-POSITION (ASCII "/") ST_CH) 2)))
  (SETQ LOC_NUM_LIST (SINGLE_ELE_LIST ENT_LIST 1))
  (SETQ ENT_LIST (SINGLE_ELE_LIST ENT_LIST 0))
  ;(SETQ ENT_LIST (SINGLE_ELE_LIST (FILTER_LIST (LIST "SINGLE_CANT_MAST" "DOUBLE_CANT_MAST" "TRIPLE_CANT_MAST") (EXTRACT_ENTITY_INFO2 (FORM_SSSET SSSET)) 1) 0))
  (SETQ ENT_LIST (EXTRACT_ENTITY_INFO ENT_LIST 1 3))
  (SETQ ENT_LIST (SORT_FUN ENT_LIST 1 0))
  (SETQ ENT_LIST (SINGLE_ELE_LIST ENT_LIST 0))
  (SETQ BS_PT (CDR (ASSOC 10 (ENTGET (NTH 0 ENT_LIST)))))
  (SETQ BS_PT1 (CDR (ASSOC 10 (ENTGET REFERENCE_TRACK))))
  (SETQ ENT_INFO (YARD_STRUCTURE_INFO (NTH 0 ENT_LIST)))
  (SETQ VALUES (GET_DYNAMIC_PROPERTIES REFERENCE_TRACK (LIST "LOM1 X" "LOM1 Y")))
  (SETQ VALUES1 (GET_DYNAMIC_PROPERTIES REFERENCE_TRACK (LIST "LNM1 X" "LNM1 Y")))
  (SETQ VALUES2 (GET_DYNAMIC_PROPERTIES REFERENCE_TRACK (LIST "LCM1 X" "LCM1 Y")))
  (SETQ VALUES3 (GET_DYNAMIC_PROPERTIES REFERENCE_TRACK (LIST "LTM1 X" "LTM1 Y")))
  ;(SETQ FDN_REFERENCE (NTH 1 (NTH 0 (GET_TEXT_ALIGNMENT_POINT (LIST (NTH 0 ENT_LIST)) "FOUNDATION_TYPE1" 0))))
  ;(SETQ RD_REFERENCE (NTH 1 (NTH 0 (GET_TEXT_ALIGNMENT_POINT (LIST (NTH 0 ENT_LIST)) "RD1" 0))))
  (SETQ POINT (LIST (+ (CAR BS_PT) (CADR (ASSOC "LOM1 X" VALUES))) (+ (CADR BS_PT1) (CADR (ASSOC "LOM1 Y" VALUES))) 0.0))
  (SETQ POINT1 (LIST (+ (CAR BS_PT) (CADR (ASSOC "LNM1 X" VALUES1))) (+ (CADR BS_PT1) (CADR (ASSOC "LNM1 Y" VALUES1))) 0.0))
  (SETQ POINT2 (LIST (+ (CAR BS_PT) (CADR (ASSOC "LCM1 X" VALUES2))) (+ (CADR BS_PT1) (CADR (ASSOC "LCM1 Y" VALUES2))) 0.0))
  (SETQ POINT3 (LIST (+ (CAR BS_PT) (CADR (ASSOC "LTM1 X" VALUES3))) (+ (CADR BS_PT1) (CADR (ASSOC "LTM1 Y" VALUES3))) 0.0))
  (SETQ ENT_LIST_SPAN (ATTRIBUTES_FROM_ENTITIES ENT_LIST "SPAN1" 0))
  (SETQ I 0)
   ;(setq dcl_id (load_dialog "DISPLAY_INFO.dcl"))
   ;(new_dialog "DISPLAY_INFO" dcl_id)
  (WHILE (< I (LENGTH ENT_LIST_SPAN))
    ;(SETQ LOC (STRCAT KM_NO "/" LOC_NO))
    (SETQ CH (STRCAT KM_NO "/" ST_CH))
     ;(SET_TILE "INFO" (STRCAT "UPDATING LOC NO "  " " "OF "  (ITOA (LENGTH ENT_LIST_SPAN))))
     ;(SET_TILE "PERCENTAGE" (STRCAT "UPDATING CHAINAGE " CH))
    ;(IF (= I (- (LENGTH ENT_LIST_SPAN) 1))
      ;(PROGN
      ;(SET_TILE "INFO" (STRCAT "ALL "  KM_NO "TH KILOMETER" " LOCATIONS ARE UPDATED SUCESSFULLY"))
      ;(SET_TILE "PERCENTAGE" "PRESS OK TO CONTINUE")
      ;)
    ;)
    
    (SETQ TEMP_ELE  (NTH I ENT_LIST_SPAN))
    (SETQ BASE_POINT (CDR (ASSOC 10 (ENTGET (NTH 0 TEMP_ELE)))))
    (MODIFY_ATTRIBUTES (NTH 0 TEMP_ELE) (LIST "MAST_NUMBER1" "CHAINAGE1") (LIST (STRCAT KM_NO "/" (NTH I LOC_NUM_LIST)) CH))
    ;(INSERT_ATTRIBUTES1 (NTH 0 TEMP_ELE) (LIST "LOM1") (LIST POINT))
    ;(INSERT_ATTRIBUTES1 (NTH 0 TEMP_ELE) (LIST "LNM1") (LIST POINT1))
    ;(INSERT_ATTRIBUTES1 (NTH 0 TEMP_ELE) (LIST "LCM1") (LIST POINT2))
    ;(INSERT_ATTRIBUTES1 (NTH 0 TEMP_ELE) (LIST "LTM1") (LIST POINT3))
    ;(IF (/= I 0)
    ;(PROGN (CHANGE_TEXT_ALIGNMENT_POINT (NTH I ENT_LIST) '("FOUNDATION_TYPE1") (LIST FDN_REFERENCE))
    ;(CHANGE_TEXT_ALIGNMENT_POINT (NTH I ENT_LIST) '("RD1") (LIST RD_REFERENCE))
    ;)
    ;)
    (SETQ TEMP_SPAN (* (ATOF (NTH 1 TEMP_ELE)) SCALE))
    (IF (/= TEMP_SPAN 0)
    (PROGN
    (SETQ POINT (LIST (+ (CAR POINT) TEMP_SPAN) (CADR POINT) 0.0))
    (SETQ POINT1 (LIST (+ (CAR POINT1) TEMP_SPAN) (CADR POINT1) 0.0))
    (SETQ POINT2 (LIST (+ (CAR POINT2) TEMP_SPAN) (CADR POINT2) 0.0))
    (SETQ POINT3 (LIST (+ (CAR POINT3) TEMP_SPAN) (CADR POINT3) 0.0))
    ;(SETQ FDN_REFERENCE (LIST (+ (CAR FDN_REFERENCE) TEMP_SPAN)  (CADR FDN_REFERENCE)  0.0))
    ;(SETQ RD_REFERENCE  (LIST (+ (CAR RD_REFERENCE) TEMP_SPAN)  (CADR RD_REFERENCE)  0.0))
    )
    (PROGN
      ;(IF (/= I (- (LENGTH ENT_LIST_SPAN) 1)) (PROGN (SET_TILE "INFO" (STRCAT "SPAN HAS NOT BEEN ENTERED IN LOC NO "     ))
     ;(SET_TILE "PERCENTAGE" (STRCAT "PROGRAM STOPPED AT CHAINAGE " CH " PLEASE CHECK..."))))
      (SETQ I (LENGTH ENT_LIST_SPAN))
    ))
    ;(SETQ LOC_NO (ITOA (+ (ATOI LOC_NO) 2)))
    (SETQ ST_CH (RTOS (+ (ATOF ST_CH) (ATOF (NTH 1 TEMP_ELE))) 2 2))
    (SETQ I (+ I 1))
    )
    ;(setq ddiag(start_dialog))
)

(DEFUN UPDATE_CHAINAGES_SPLIT (SCALE ST_CH ENT_LIST REFERENCE_TRACK / SSSET LOC_NO ST_CH LOC_NUM_LIST ENT_LIST BS_PT BS_PT1 ENT_INFO VALUES VALUES1 VALUES2 VALUES3 VALUES4 FDN_REFERENCE FDN_REFERENCE_X FDN_REFERENCE_Y RD_REFERENCE RD_REFERENCE_X RD_REFERENCE_Y TC_REFERENCE TC_REFERENCE_X TC_REFERENCE_Y SPAN_REFERENCE_X SPAN_REFERENCE_Y ENT_LIST_SPAN POINT POINT1 POINT2 POINT3 ENT_LIST_SPAN VISIBILITY_SPAN VISIBILITY_TC VISIBILITY_FDN VISIBILITY_RD I LOC CH TEMP_ELE SCALE POINT_FDN POINT_RD POINT_TC TEMP_SPAN)
  ;(PROMPT "\n SELECT MASTS")
  ;(SETQ SSSET (SSGET))
  ;(SETQ SCALE (GETREAL "\n ENTER SCALE : "))
  ;(SETQ LOC_NO (GETSTRING "\n ENTER STARTING MAST LOCATION NUMBER :"))
  ;(SETQ ST_CH (GETSTRING "\n ENTER STARTING MAST CHAINAGE :"))
  (SETQ	KM_NO (SUBSTR ST_CH 1 (VL-STRING-POSITION (ASCII "/") ST_CH)))
  ;(SETQ	LOC_NO	(SUBSTR	LOC_NO (+ (VL-STRING-POSITION (ASCII "/") LOC_NO) 2)))
  (SETQ	ST_CH	(SUBSTR	ST_CH (+ (VL-STRING-POSITION (ASCII "/") ST_CH) 2)))
  (SETQ LOC_NUM_LIST (SINGLE_ELE_LIST ENT_LIST 1))
  (SETQ ENT_LIST (SINGLE_ELE_LIST ENT_LIST 0))
  ;(SETQ ENT_LIST (SINGLE_ELE_LIST (FILTER_LIST (LIST "SINGLE_CANT_MAST" "DOUBLE_CANT_MAST" "TRIPLE_CANT_MAST") (EXTRACT_ENTITY_INFO2 (FORM_SSSET SSSET)) 1) 0))
  (SETQ ENT_LIST (EXTRACT_ENTITY_INFO ENT_LIST 1 3))
  (SETQ ENT_LIST (SORT_FUN ENT_LIST 1 0))
  (SETQ ENT_LIST (SINGLE_ELE_LIST ENT_LIST 0))
  (SETQ BS_PT (CDR (ASSOC 10 (ENTGET (NTH 0 ENT_LIST)))))
  (SETQ BS_PT1 (CDR (ASSOC 10 (ENTGET REFERENCE_TRACK))))
  (SETQ ENT_INFO (YARD_STRUCTURE_INFO (NTH 0 ENT_LIST)))
  (SETQ VALUES (GET_DYNAMIC_PROPERTIES REFERENCE_TRACK (LIST "LOM1 X" "LOM1 Y")))
  (SETQ VALUES1 (GET_DYNAMIC_PROPERTIES REFERENCE_TRACK (LIST "LNM1 X" "LNM1 Y")))
  (SETQ VALUES2 (GET_DYNAMIC_PROPERTIES REFERENCE_TRACK (LIST "LCM1 X" "LCM1 Y")))
  (SETQ VALUES3 (GET_DYNAMIC_PROPERTIES REFERENCE_TRACK (LIST "LTM1 X" "LTM1 Y")))
  ;(SETQ FDN_REFERENCE (NTH 1 (NTH 0 (GET_TEXT_ALIGNMENT_POINT (LIST (NTH 0 ENT_LIST)) "FOUNDATION_TYPE1" 0))))
  ;(SETQ RD_REFERENCE (NTH 1 (NTH 0 (GET_TEXT_ALIGNMENT_POINT (LIST (NTH 0 ENT_LIST)) "RD1" 0))))
  (SETQ POINT (LIST (+ (CAR BS_PT) (CADR (ASSOC "LOM1 X" VALUES))) (+ (CADR BS_PT1) (CADR (ASSOC "LOM1 Y" VALUES))) 0.0))
  (SETQ POINT1 (LIST (+ (CAR BS_PT) (CADR (ASSOC "LNM1 X" VALUES1))) (+ (CADR BS_PT1) (CADR (ASSOC "LNM1 Y" VALUES1))) 0.0))
  (SETQ POINT2 (LIST (+ (CAR BS_PT) (CADR (ASSOC "LCM1 X" VALUES2))) (+ (CADR BS_PT1) (CADR (ASSOC "LCM1 Y" VALUES2))) 0.0))
  (SETQ POINT3 (LIST (+ (CAR BS_PT) (CADR (ASSOC "LTM1 X" VALUES3))) (+ (CADR BS_PT1) (CADR (ASSOC "LTM1 Y" VALUES3))) 0.0))
  (SETQ ENT_LIST_SPAN (ATTRIBUTES_FROM_ENTITIES ENT_LIST "SPAN1" 0))
  (SETQ I 0)
   ;(setq dcl_id (load_dialog "DISPLAY_INFO.dcl"))
   ;(new_dialog "DISPLAY_INFO" dcl_id)
  (WHILE (< I (LENGTH ENT_LIST_SPAN))
    ;(SETQ LOC (STRCAT KM_NO "/" LOC_NO))
    (SETQ CH (STRCAT KM_NO "/" ST_CH))
     ;(SET_TILE "INFO" (STRCAT "UPDATING LOC NO "  " " "OF "  (ITOA (LENGTH ENT_LIST_SPAN))))
     ;(SET_TILE "PERCENTAGE" (STRCAT "UPDATING CHAINAGE " CH))
    ;(IF (= I (- (LENGTH ENT_LIST_SPAN) 1))
      ;(PROGN
      ;(SET_TILE "INFO" (STRCAT "ALL "  KM_NO "TH KILOMETER" " LOCATIONS ARE UPDATED SUCESSFULLY"))
      ;(SET_TILE "PERCENTAGE" "PRESS OK TO CONTINUE")
      ;)
    ;)
    
    (SETQ TEMP_ELE  (NTH I ENT_LIST_SPAN))
    (SETQ BASE_POINT (CDR (ASSOC 10 (ENTGET (NTH 0 TEMP_ELE)))))
    (MODIFY_ATTRIBUTES (NTH 0 TEMP_ELE) (LIST "MAST_NUMBER1" "CHAINAGE1") (LIST (STRCAT KM_NO "/" (NTH I LOC_NUM_LIST)) CH))
    (INSERT_ATTRIBUTES1 (NTH 0 TEMP_ELE) (LIST "LOM1") (LIST POINT))
    (INSERT_ATTRIBUTES1 (NTH 0 TEMP_ELE) (LIST "LNM1") (LIST POINT1))
    (INSERT_ATTRIBUTES1 (NTH 0 TEMP_ELE) (LIST "LCM1") (LIST POINT2))
    (INSERT_ATTRIBUTES1 (NTH 0 TEMP_ELE) (LIST "LTM1") (LIST POINT3))
    ;(IF (/= I 0)
    ;(PROGN (CHANGE_TEXT_ALIGNMENT_POINT (NTH I ENT_LIST) '("FOUNDATION_TYPE1") (LIST FDN_REFERENCE))
    ;(CHANGE_TEXT_ALIGNMENT_POINT (NTH I ENT_LIST) '("RD1") (LIST RD_REFERENCE))
    ;)
    ;)
    (SETQ TEMP_SPAN (* (ATOF (NTH 1 TEMP_ELE)) SCALE))
    (IF (/= TEMP_SPAN 0)
    (PROGN
    (SETQ POINT (LIST (+ (CAR POINT) TEMP_SPAN) (CADR POINT) 0.0))
    (SETQ POINT1 (LIST (+ (CAR POINT1) TEMP_SPAN) (CADR POINT1) 0.0))
    (SETQ POINT2 (LIST (+ (CAR POINT2) TEMP_SPAN) (CADR POINT2) 0.0))
    (SETQ POINT3 (LIST (+ (CAR POINT3) TEMP_SPAN) (CADR POINT3) 0.0))
    ;(SETQ FDN_REFERENCE (LIST (+ (CAR FDN_REFERENCE) TEMP_SPAN)  (CADR FDN_REFERENCE)  0.0))
    ;(SETQ RD_REFERENCE  (LIST (+ (CAR RD_REFERENCE) TEMP_SPAN)  (CADR RD_REFERENCE)  0.0))
    )
    (PROGN
      ;(IF (/= I (- (LENGTH ENT_LIST_SPAN) 1)) (PROGN (SET_TILE "INFO" (STRCAT "SPAN HAS NOT BEEN ENTERED IN LOC NO "     ))
     ;(SET_TILE "PERCENTAGE" (STRCAT "PROGRAM STOPPED AT CHAINAGE " CH " PLEASE CHECK..."))))
      (SETQ I (LENGTH ENT_LIST_SPAN))
    ))
    ;(SETQ LOC_NO (ITOA (+ (ATOI LOC_NO) 2)))
    (SETQ ST_CH (RTOS (+ (ATOF ST_CH) (ATOF (NTH 1 TEMP_ELE))) 2 2))
    (SETQ I (+ I 1))
    )
    ;(setq ddiag(start_dialog))
)





;                                                   ;AUTOCAD(LOP) TO EXCEL DATA DUMPING FUNCTIONS;                                         
;                                                                                                                                          
;         CONTENTS 1)SUPPORTING/GENERAL FUNCTIONS                                                                                          
;                  2)DATA EXTRACTION FUNCTIONS FROM LOP BLOCKS                                                                             
;                  3)DATA MANIPULATION FUNCTIONS FOR DATA EXTRACTED FROM LOP BLOCKS                                                        
;                  4)DATA DUMPING FUNCTIONS INTO EXCEL                                                                                     
;                  5)DATA EXTRACTION FUNCTIONS FROM EXCEL                                                                                  
;                  6)DATA DUMPING FUNCTIONS IN TO ACAD TABLES                                                                              
;                                                                                                                                          

;**************************************************1)SUPPORTING/GENERAL FUNCTIONS********************************************;
 
                                               ;   ;SUPPORTING/GENERAL FUNCTIONS-1   
                                               ;FUNCTION FOR ARRANGING LIST IN ORDER 
                                               ;    ; CAN BE USED AS GENERAL FUNCTION

;USAGE:  (FRAME_LIST (LIST 1 2 3 4) (LIST '(2 3) (3 2) (1 2) (4 1)) 0)                                                    
;        LIST1--> (LIST 1 2 3 4) -->LIST PATTERN WHICH ARRANGES THE LIST2 IN ITS ORDER WRT FLAG ELEMENT                   
;        LIST2--> (LIST '(2 3) (3 2) (1 2) (4 1)) -->LIST TO BE ARRANGED                                                  
;        FLAG---> 0 ELEMENT NUMBER REFERENCE                                                                              
; FLAG---> 0==>OUTPUT---> ((1 1) (2 2) (3 3) (4 4))                                                                       
; FLAG---> 1==>OUTPUT---> ((1 2) (2 3) (3 2) (4 1))                                                                       
;  EG2:  LIST1-->(LIST 1 2 3 4)    LIST2-->(LIST '(2 3) (3 2) (1 2))--->OUTPUT==> ((1 2) (2 3) (3 2) (4 NIL)) FOR FLAG==>1
;                                                                                                                         

;;;;;;;;;;;;;;;;;;;;
(DEFUN FRAME_LIST (LIST1 LIST2 FLAG / I TEMP_ELE LIST3)
  (SETQ I 0)
  (SETQ TEMP_ELE NIL)
  (SETQ LIST3 NIL)
  (WHILE (< I (LENGTH LIST1))
    (SETQ TEMP_ELE (ASSOC (NTH I LIST1) LIST2))
    (IF (/= TEMP_ELE NIL)
      (SETQ LIST3 (CONS (LIST (NTH I LIST1) (NTH FLAG TEMP_ELE)) LIST3))
      (SETQ LIST3 (CONS (LIST (NTH I LIST1) NIL) LIST3))
    )
   (SETQ I (+ I 1))
  )
  (REVERSE LIST3)
)
;;;;;;;;;;;;;;;;;;;




(DEFUN UPDATE_TL (LIST1 LIST2 / ATTR_SET1 ATTR_SET2 MAST1_ATTR MAST2_ATTR MAST1_POINT MAST2_POINT  TL)
  (SETQ ATTR_SET1 (GET_ATTRIBUTES1 (NTH 0 LIST1)))
  (SETQ ATTR_SET2 (GET_ATTRIBUTES1 (NTH 0 LIST2)))
  (SETQ MAST1_ATTR (FRAME_LIST (LIST "MAST_NUMBER1" "CHAINAGE1") ATTR_SET1 1))
  (SETQ MAST2_ATTR (FRAME_LIST (LIST "MAST_NUMBER1" "CHAINAGE1") ATTR_SET2 1))
  (SETQ MAST1_POINT (CDR(ASSOC 10 (ENTGET(NTH 0 LIST1)))))
  (SETQ MAST2_POINT (CDR(ASSOC 10 (ENTGET(NTH 0 LIST2)))))
  (SETQ TL (RTOS (ABS (- (CAR MAST1_POINT) (CAR MAST2_POINT))) 2 2))
  (MODIFY_ATTRIBUTES (NTH 1 LIST1) (LIST "TENSION_LENGTH" "LOCATION_NUM" "CHAINAGE") (LIST TL (NTH 1 (ASSOC "MAST_NUMBER1" MAST2_ATTR)) (NTH 1 (ASSOC "CHAINAGE1" MAST2_ATTR))))
  (MODIFY_ATTRIBUTES (NTH 1 LIST2) (LIST "TENSION_LENGTH" "LOCATION_NUM" "CHAINAGE") (LIST TL (NTH 1 (ASSOC "MAST_NUMBER1" MAST1_ATTR)) (NTH 1 (ASSOC "CHAINAGE1" MAST1_ATTR))))
)



(DEFUN DATA_TO_STRUCTURE_MAP_SECTIONING (LIST1 LIST2 K Q  / I TEMP_ELE TEMP_ELE1 LIST3)
(SETQ I 0)
(SETQ TEMP_ELE NIL)
(SETQ TEMP_ELE1 NIL)
(SETQ LIST3 NIL)
(WHILE (< I (LENGTH LIST1))
  (SETQ TEMP_ELE1 (MAP_NEAREST1 LIST2 (NTH K (NTH I LIST1)) Q ))
  (SETQ TEMP_ELE (APPEND (LIST (NTH 0 (NTH I LIST1))) TEMP_ELE1 ))
  (SETQ LIST3 (CONS TEMP_ELE LIST3))
  ;(SETQ LIST2 (VL-REMOVE TEMP_ELE1 LIST2))
  (SETQ I (+ I 1))
  )
LIST3
)



(DEFUN C:UPDATE_TENSION_LENGTHS ( / I WPT1 WPT2 BLOCKS_LIST MAST_UP MAST_DN BLOCK_NAME_LIST ACC_LIST OLC_LIST TL_LIST MAST_TTC ANCHOR_ENTITIES ANCHOR_START ANCHOR_END MAIN_LIST )
  (SETQ WPT1 (GETPOINT "ENTER STARTING POINT IN LOP"))
  (SETQ WPT2 (GETPOINT "\n ENTER ENDING POINT IN LOP"))
  (SETQ BLOCKS_LIST (FORM_SSSET (SSGET "W" WPT1 WPT2 (LIST (CONS 0 "INSERT")))))
  (SETQ BLOCK_NAME_LIST (EXTRACT_ENTITY_INFO2 BLOCKS_LIST))
  (SETQ ACC_LIST (FILTER_LIST (LIST "ACC") BLOCK_NAME_LIST 1))
  (SETQ OLC_LIST (FILTER_LIST (LIST "OLC") BLOCK_NAME_LIST 1))
  (SETQ TL_LIST (FILTER_LIST (LIST "TENSION_LENGTH") BLOCK_NAME_LIST 1))
  (SETQ ACC_LIST (BUILD_LIST (ENTITY_DFX (SINGLE_ELE_LIST ACC_LIST 0) 10 -1) (LIST 0 1)))
  (SETQ OLC_LIST (BUILD_LIST (ENTITY_DFX (SINGLE_ELE_LIST OLC_LIST 0) 10 -1) (LIST 0 1)))
  (SETQ TL_LIST  (BUILD_LIST (ENTITY_DFX (SINGLE_ELE_LIST TL_LIST 0)  10 -1) (LIST 0 1)))
  ;(COMMAND "BURST" (ENTLAST))
  (SETQ MAST_TTC (YARD_DATA_COLLECT WPT1 WPT2 '("SINGLE_CANT_MAST" "DOUBLE_CANT_MAST" "TRIPLE_CANT_MAST" "TTC" "SS0" "SS1" "SS2" "SS3" "SS4") 1 3))
  (SETQ MAST_TTC_DIR (YARD_DATA_COLLECT WPT1 WPT2 '("SINGLE_CANT_MAST" "DOUBLE_CANT_MAST" "TRIPLE_CANT_MAST" "TTC" "SS0" "SS1" "SS2" "SS3" "SS4") 1 5))
  ;(SETQ ANCHOR_LIST (YARD_DATA_COLLECT WPT1 WPT2 '("ANCHOR") 1 3))
 (SETQ ANCHOR_ENTITIES (YARD_DATA_COLLECT WPT1 WPT2 '("ANCHOR") 1 5))
 (SETQ BTB_ANCHOR_ENTITIES (YARD_DATA_COLLECT WPT1 WPT2 '("BTB_ANC") 1 3))
 (SETQ ANCHOR_START (FILTER_LIST '("START") ANCHOR_ENTITIES 1))
 (SETQ ANCHOR_END (FILTER_LIST '("END") ANCHOR_ENTITIES 1))
  
 (SETQ MAST_UP (FILTER_LIST '("UP") MAST_TTC_DIR 1))
 (SETQ MAST_DN (FILTER_LIST '("DN") MAST_TTC_DIR 1))
  
 (SETQ ANCHOR_START  (BUILD_LIST (ENTITY_DFX (SINGLE_ELE_LIST ANCHOR_START 0)  10 -1) (LIST 0 1)))
 (SETQ ANCHOR_END  (BUILD_LIST (ENTITY_DFX (SINGLE_ELE_LIST ANCHOR_END 0)  10 -1) (LIST 0 1)))

  
  (IF (/= ANCHOR_START NIL) (SETQ ANCHOR_START_STRUCTURE_MAP_DATA (DATA_TO_STRUCTURE_MAP_SECTIONING ANCHOR_START MAST_TTC 1 1)) (SETQ ANCHOR_START NIL))
  (IF (/= ANCHOR_END NIL) (SETQ ANCHOR_END_STRUCTURE_MAP_DATA (DATA_TO_STRUCTURE_MAP_SECTIONING ANCHOR_END MAST_TTC 1 1)) (SETQ ANCHOR_END NIL))
  
  (IF (/= ACC_LIST NIL) (SETQ ACC_STRUCTURE_MAP_DATA (DATA_TO_STRUCTURE_MAP_SECTIONING ACC_LIST MAST_TTC 1 1)) (SETQ ACC_STRUCTURE_MAP_DATA NIL))
  (IF (/= OLC_LIST NIL) (SETQ OLC_STRUCTURE_MAP_DATA (DATA_TO_STRUCTURE_MAP1 OLC_LIST MAST_TTC 1 1)) (SETQ OLC_STRUCTURE_MAP_DATA NIL))
  (IF (/= TL_LIST NIL) (SETQ TL_STRUCTURE_MAP_DATA (DATA_TO_STRUCTURE_MAP_SECTIONING TL_LIST MAST_TTC 1 1)) (SETQ TL_STRUCTURE_MAP_DATA NIL))
  (SETQ MAIN_LIST (MAP_TENSION_LENGTHS ANCHOR_START_STRUCTURE_MAP_DATA ANCHOR_END_STRUCTURE_MAP_DATA TL_STRUCTURE_MAP_DATA))

  (SETQ I 0)
  (WHILE (< I (LENGTH MAIN_LIST))
  (UPDATE_TL (NTH 0 (NTH I MAIN_LIST)) (NTH 1 (NTH I MAIN_LIST)))
  (SETQ I (+ I 1))
  )
  
  (SETQ MAST_UP  (ADD_LISTS (BUILD_LIST (ENTITY_DFX (SINGLE_ELE_LIST MAST_UP 0)  10 -1) (LIST 0 1)) (N_ELE_LIST "UP" (LENGTH MAST_UP))))
  (SETQ MAST_DN  (ADD_LISTS (BUILD_LIST (ENTITY_DFX (SINGLE_ELE_LIST MAST_DN 0)  10 -1) (LIST 0 1)) (N_ELE_LIST "DN" (LENGTH MAST_DN))))

  (IF (/= BTB_ANCHOR_ENTITIES NIL) (SETQ BTB_ANCHOR_STRUCTURE_MAP_DATA_TOTAL (DATA_TO_STRUCTURE_MAP_SECTIONING BTB_ANCHOR_ENTITIES (APPEND MAST_UP MAST_DN) 1 1)) (SETQ BTB_ANCHOR_ENTITIES NIL))
  (SETQ BTB_ANCHOR_STRUCTURE_MAP_DATA_TOTAL (BUILD_LIST (SORT_FUN (ADD_LISTS BTB_ANCHOR_STRUCTURE_MAP_DATA_TOTAL (SINGLE_ELE_LIST (ENTITY_DFX (SINGLE_ELE_LIST BTB_ANCHOR_STRUCTURE_MAP_DATA_TOTAL 0)  10 -1) 1)) 2 0) (LIST 0 1 3)))
  (SETQ BTB_ANCHOR_STRUCTURE_MAP_DATA_TOTAL (ADD_LISTS BTB_ANCHOR_STRUCTURE_MAP_DATA_TOTAL (SINGLE_ELE_LIST (ATTRIBUTES_FROM_ENTITIES (SINGLE_ELE_LIST BTB_ANCHOR_STRUCTURE_MAP_DATA_TOTAL 0) "ANCHOR_TYPE1" 1) 1)))
  (UPDATE_BTB_TL (FILTER_LIST (LIST "FA")  (FILTER_LIST (LIST "UP") BTB_ANCHOR_STRUCTURE_MAP_DATA_TOTAL 2) 3) TL_STRUCTURE_MAP_DATA)
  (UPDATE_BTB_TL (FILTER_LIST (LIST "FA")  (FILTER_LIST (LIST "DN") BTB_ANCHOR_STRUCTURE_MAP_DATA_TOTAL 2) 3) TL_STRUCTURE_MAP_DATA)
  (UPDATE_BTB_TL (FILTER_LIST (LIST "AEWA")  (FILTER_LIST (LIST "UP") BTB_ANCHOR_STRUCTURE_MAP_DATA_TOTAL 2) 3) TL_STRUCTURE_MAP_DATA)
  (UPDATE_BTB_TL (FILTER_LIST (LIST "AEWA")  (FILTER_LIST (LIST "DN") BTB_ANCHOR_STRUCTURE_MAP_DATA_TOTAL 2) 3) TL_STRUCTURE_MAP_DATA)

 (SETQ START_END_MAST_LIST_FOR_ACC_UP (FILTER_LIST (SINGLE_ELE_LIST MAST_UP 0) (ADD_LISTS1 (SINGLE_ELE_LIST (SINGLE_ELE_LIST MAIN_LIST 0) 0) (SINGLE_ELE_LIST (SINGLE_ELE_LIST MAIN_LIST 1) 0)) 0))
 (SETQ START_END_MAST_LIST_FOR_ACC_DN (FILTER_LIST (SINGLE_ELE_LIST MAST_DN 0) (ADD_LISTS1 (SINGLE_ELE_LIST (SINGLE_ELE_LIST MAIN_LIST 0) 0) (SINGLE_ELE_LIST (SINGLE_ELE_LIST MAIN_LIST 1) 0)) 0))
 (SETQ MAST_LIST_FOR_ACC_UP (BREAK_MAST_WIRE_LENGTH START_END_MAST_LIST_FOR_ACC_UP (BUILD_LIST (ENTITY_DFX (SINGLE_ELE_LIST MAST_UP 0) 10 -1) (LIST 0 1))))
 (SETQ MAST_LIST_FOR_ACC_DN (BREAK_MAST_WIRE_LENGTH START_END_MAST_LIST_FOR_ACC_DN (BUILD_LIST (ENTITY_DFX (SINGLE_ELE_LIST MAST_DN 0) 10 -1) (LIST 0 1))))
 (UPDATE_ACC_LIST MAST_LIST_FOR_ACC_UP ACC_STRUCTURE_MAP_DATA)
 (UPDATE_ACC_LIST MAST_LIST_FOR_ACC_DN ACC_STRUCTURE_MAP_DATA)
 (UPDATE_OLC_CHAINAGE OLC_STRUCTURE_MAP_DATA)
)



(DEFUN FIND_IN_BETWEEN (LIST1 LIST2 A B C / I FINAL_LIST TEMP_ELE1 TEMP_ELE2 J TEMP_LIST TEMP_ELE3)
  (SETQ I 1 FINAL_LIST NIL)
  (WHILE (< I (LENGTH LIST1))
    (SETQ TEMP_ELE1 (NTH A (NTH (- I 1) LIST1)) TEMP_ELE2 (NTH A (NTH I LIST1)))
    (SETQ J 0 TEMP_LIST NIL)
    (WHILE (< J (LENGTH LIST2))
      (SETQ TEMP_ELE3 (NTH B (NTH C (NTH J LIST2))))
      (IF (AND (> TEMP_ELE3 TEMP_ELE1) (< TEMP_ELE3 TEMP_ELE2)) (SETQ TEMP_LIST (CONS (NTH J LIST2) TEMP_LIST)))
      (SETQ J (+ J 1))
    )
    (SETQ FINAL_LIST (CONS TEMP_LIST FINAL_LIST))
    (SETQ I (+ I 1))
  )
  (REVERSE FINAL_LIST)
)




(DEFUN UPDATE_BTB_TL ( BTB_ANCHOR_STRUCTURE_MAP_DATA TL_STRUCTURE_MAP_DATA / I TEMP_MAST1 TEMP_TL_LIST1 TL_ST1 TEMP_ELE1 TEMP_MAST2 TEMP_TL_LIST2 TL_ST2 TEMP_ELE2)
  (SETQ I 0 TEMP_MAST1 NIL TEMP_TL_LIST1 NIL TL_ST1 NIL TEMP_ELE1 NIL TEMP_MAST2 NIL TEMP_TL_LIST2 NIL TL_ST2 NIL TEMP_ELE2 NIL)
  (WHILE (< I (LENGTH BTB_ANCHOR_STRUCTURE_MAP_DATA))
    (SETQ TEMP_MAST1 (NTH 1 (NTH I BTB_ANCHOR_STRUCTURE_MAP_DATA)))
    (SETQ TEMP_TL_LIST1 (SINGLE_ELE_LIST (FILTER_LIST (LIST TEMP_MAST1) TL_STRUCTURE_MAP_DATA 1) 0))
    (IF (= (NTH 1 (NTH 0 (GET_DYNAMIC_PROPERTIES (NTH 0 TEMP_TL_LIST1) (LIST "TLF2")))) 1) (SETQ TL_ST1 (NTH 0 TEMP_TL_LIST1)) (SETQ TL_ST1 (NTH 1 TEMP_TL_LIST1)))
    (SETQ TEMP_ELE1 (LIST (NTH 1 (NTH I BTB_ANCHOR_STRUCTURE_MAP_DATA)) TL_ST1))
    (IF (/= (NTH (+ I 1) BTB_ANCHOR_STRUCTURE_MAP_DATA) NIL)
    (PROGN
    (SETQ TEMP_MAST2 (NTH 1 (NTH (+ I 1) BTB_ANCHOR_STRUCTURE_MAP_DATA)))
    (SETQ TEMP_TL_LIST2 (SINGLE_ELE_LIST (FILTER_LIST (LIST TEMP_MAST2) TL_STRUCTURE_MAP_DATA 1) 0))
    (IF (= (NTH 1 (NTH 0 (GET_DYNAMIC_PROPERTIES (NTH 0 TEMP_TL_LIST2) (LIST "TLF2")))) 0) (SETQ TL_ST2 (NTH 0 TEMP_TL_LIST2)) (SETQ TL_ST2 (NTH 1 TEMP_TL_LIST2)))
    (SETQ TEMP_ELE2 (LIST (NTH 1 (NTH (+ I 1) BTB_ANCHOR_STRUCTURE_MAP_DATA)) TL_ST2))
    (UPDATE_TL TEMP_ELE1 TEMP_ELE2)
    ))
    (SETQ I (+ I 1))
  )
)




(DEFUN UPDATE_OLC_CHAINAGE (OLC_LIST / I TEMP_OLC TEMP_MAST TEMP_CHAINAGE )
  (SETQ I 0 TEMP_OLC NIL TEMP_MAST NIL TEMP_CHAINAGE NIL)
  (WHILE (< I (LENGTH OLC_LIST))
    (SETQ TEMP_OLC (NTH 0 (NTH I OLC_LIST)))
    (SETQ TEMP_MAST (NTH 1 (NTH I OLC_LIST)))
    (SETQ TEMP_CHAINAGE (NTH 1 (ASSOC "CHAINAGE1" (GET_ATTRIBUTES1 TEMP_MAST))))
    (MODIFY_ATTRIBUTES TEMP_OLC (LIST "CHAINAGE") (LIST (STRCAT "CH: " TEMP_CHAINAGE)))
    (SETQ I (+ I 1))
  )
)

(DEFUN MAP_TENSION_LENGTHS ( ANCHOR_START_STRUCTURE_MAP_DATA ANCHOR_END_STRUCTURE_MAP_DATA TL_STRUCTURE_MAP_DATA / I TEMP_WIRE_RUN TEMP_ELE TEMP_TL1 TEMP_TL2 TEMP_LIST FINAL_LIST )
  (SETQ I 0 TEMP_WIRE_RUN NIL TEMP_ELE NIL TEMP_TL1 NIL TEMP_TL2 NIL TEMP_LIST NIL FINAL_LIST NIL)
  (SETQ ANCHOR_START_STRUCTURE_MAP_DATA (BUILD_LIST (ADD_LISTS ANCHOR_START_STRUCTURE_MAP_DATA (SINGLE_ELE_LIST (ATTRIBUTES_FROM_ENTITIES (SINGLE_ELE_LIST ANCHOR_START_STRUCTURE_MAP_DATA 0) "WIRE_RUN1" 0) 1)) (LIST 3 0 1)))
  (SETQ ANCHOR_END_STRUCTURE_MAP_DATA (BUILD_LIST (ADD_LISTS ANCHOR_END_STRUCTURE_MAP_DATA (SINGLE_ELE_LIST (ATTRIBUTES_FROM_ENTITIES (SINGLE_ELE_LIST ANCHOR_END_STRUCTURE_MAP_DATA 0) "WIRE_RUN1" 0) 1)) (LIST 3 0 1)))
  (SETQ TL_STRUCTURE_MAP_DATA (BUILD_LIST TL_STRUCTURE_MAP_DATA (LIST 1 0)))
  (WHILE (< I (LENGTH ANCHOR_START_STRUCTURE_MAP_DATA))
    (SETQ TEMP_ELE (ASSOC (NTH 0 (NTH I ANCHOR_START_STRUCTURE_MAP_DATA)) ANCHOR_END_STRUCTURE_MAP_DATA))
    (IF (/= TEMP_ELE NIL)
     (PROGN
      (SETQ TEMP_TL1 (ASSOC (NTH 2 (NTH I ANCHOR_START_STRUCTURE_MAP_DATA)) TL_STRUCTURE_MAP_DATA))
      (SETQ TEMP_TL2 (ASSOC (NTH 2 TEMP_ELE) TL_STRUCTURE_MAP_DATA))
      (IF (AND (/= TEMP_TL1 NIL) (/= TEMP_TL2 NIL))
      (PROGN
      (SETQ TEMP_LIST (LIST (LIST (NTH 2 (NTH I ANCHOR_START_STRUCTURE_MAP_DATA)) (NTH 1 TEMP_TL1)) (LIST (NTH 2 TEMP_ELE) (NTH 1 TEMP_TL2))))
      (SETQ FINAL_LIST (CONS TEMP_LIST FINAL_LIST))
      )
      )
     )
    )
   (SETQ I (+ I 1))
  )
 (REVERSE FINAL_LIST)
)



(DEFUN BREAK_MAST_WIRE_LENGTH (START_END_MAST_LIST TOTAL_MAST_LIST / I TEMP_ELE TEMP_LIST FINAL_LIST)
  (SETQ I 0 TEMP_ELE NIL TEMP_LIST NIL FINAL_LIST NIL)
    (WHILE (< I (LENGTH START_END_MAST_LIST))
    (SETQ TEMP_LIST (BUILD_LIST (ENTITY_DFX (NTH I START_END_MAST_LIST) 10 -1) (LIST 0 1)))
    (SETQ TEMP_ELE (SORT_FUN (APPEND (NTH 0 (FIND_IN_BETWEEN (SINGLE_ELE_LIST TEMP_LIST 1) TOTAL_MAST_LIST 0 0 1)) TEMP_LIST) 1 0))
    (SETQ FINAL_LIST (CONS TEMP_ELE FINAL_LIST))
    (SETQ I (+ I 1))
    )
(REVERSE FINAL_LIST)
)


(DEFUN UPDATE_ACC_LIST ( MAST_LIST ACC_STRUCTURE_MAP_DATA / I TEMP_ACC_MAST_DATA TEMP_POSITION TEMP_LEFT_COUNT TEMP_RIGHT_COUNT TEMP_LEFT_LENGTH TEMP_RIGHT_LENGTH)
  (SETQ I 0 TEMP_ACC_MAST_DATA NIL TEMP_POSITION NIL TEMP_LEFT_COUNT NIL TEMP_RIGHT_COUNT NIL TEMP_LEFT_LENGTH NIL TEMP_RIGHT_LENGTH NIL)
  (WHILE (< I (LENGTH MAST_LIST))
    (IF (/= (FILTER_LIST (SINGLE_ELE_LIST (NTH I MAST_LIST)  0) ACC_STRUCTURE_MAP_DATA 1) NIL)
    (PROGN
    (SETQ TEMP_ACC_MAST_DATA (NTH 0 (FILTER_LIST (SINGLE_ELE_LIST (NTH I MAST_LIST)  0) ACC_STRUCTURE_MAP_DATA 1)))
    (SETQ TEMP_POSITION (VL-POSITION (NTH 1 TEMP_ACC_MAST_DATA) (SINGLE_ELE_LIST (NTH I MAST_LIST)  0)))
    (SETQ TEMP_LEFT_COUNT (RTOS TEMP_POSITION 2 0))
    (SETQ TEMP_RIGHT_COUNT (RTOS (- (- (LENGTH (NTH I MAST_LIST)) TEMP_POSITION) 1) 2 0))
    (SETQ TEMP_LEFT_LENGTH (RTOS (ABS (- (NTH 0 (NTH 1 (NTH 0 (NTH I MAST_LIST)))) (NTH 0 (NTH 2 TEMP_ACC_MAST_DATA)))) 2 2))
    (SETQ TEMP_RIGHT_LENGTH (RTOS (ABS  (- (NTH 0 (NTH 2 TEMP_ACC_MAST_DATA)) (NTH 0 (NTH 1 (NTH (- (LENGTH (NTH I MAST_LIST)) 1) (NTH I MAST_LIST)))))) 2 2))
    (MODIFY_ATTRIBUTES (NTH 0 TEMP_ACC_MAST_DATA) (LIST "MAST_COUNT1" "MAST_COUNT2" "TENSION_LENGTH1" "TENSION_LENGTH2") (LIST TEMP_LEFT_COUNT TEMP_RIGHT_COUNT TEMP_LEFT_LENGTH TEMP_RIGHT_LENGTH))
    )
    )
    (SETQ I (+ I 1))
  )
)

(DEFUN C:OFFSET_DISTANCE ( / OFFSET_ENTITIES TRACK_ENTITY I TEMP_ELE1 TEMP_ELE2 LIST2 )
  (PROMPT "SELECT OFFSETS")
  (SETQ OFFSET_ENTITIES1 (SSGET))
  (SETQ TRACK_ENTITY (CAR(ENTSEL "\nSELECT TRACK ALIGNMENT:")))
  (SETQ LINE (GETSTRING "\n ENTER TRACK TYPE (UP/DN)"))
  (SETQ TR_OFFSET_Y (NTH 2 (ASSOC 10 (ENTGET TRACK_ENTITY))))
  (SETQ OFFSET_ENTITIES1 (FORM_SSSET OFFSET_ENTITIES1))
  (SETQ I 0)
  (SETQ OFFSET_ENTITIES NIL)
  (WHILE (< I (LENGTH OFFSET_ENTITIES1))
    (SETQ TEMP_ELE1 (CDR (ASSOC 10 (ENTGET (NTH I OFFSET_ENTITIES1)))))
    (SETQ OFFSET_ENTITIES (CONS (LIST (NTH I OFFSET_ENTITIES1) TEMP_ELE1) OFFSET_ENTITIES))
    (SETQ I (+ I 1))
  )
  (SETQ OFFSET_ENTITIES (REVERSE OFFSET_ENTITIES))
  (SETQ OFFSET_ENTITIES (SORT_FUN OFFSET_ENTITIES 1 0))
  
  (SETQ I 0)
  (SETQ TEMP_ELE1 NIL)
  (SETQ TEMP_ELE2 NIL)
  (SETQ LIST2 NIL)
  (WHILE (< I (LENGTH OFFSET_ENTITIES))
  (SETQ TEMP_ELE1 (NTH 0 (ACET-GEOM-INTERSECTWITH TRACK_ENTITY (NTH 0 (NTH I OFFSET_ENTITIES)) 0.1)))
  (IF (/= (+ I 1) (LENGTH OFFSET_ENTITIES))
  (PROGN 
  (IF (= LINE "UP")
    (COMMAND "DIMLINEAR" (NTH 1 (NTH I OFFSET_ENTITIES)) (NTH 1 (NTH (+ I 1) OFFSET_ENTITIES))  (LIST (+ (CAR (NTH 1 (NTH I OFFSET_ENTITIES))) (/ (ABS (- (CAR (NTH 1 (NTH (+ I 1) OFFSET_ENTITIES))) (CAR (NTH 1 (NTH I OFFSET_ENTITIES))))) 2)) (+ TR_OFFSET_Y 20) 0.0))
  )
  (IF (= LINE "DN")
    (COMMAND "DIMLINEAR" (NTH 1 (NTH I OFFSET_ENTITIES)) (NTH 1 (NTH (+ I 1) OFFSET_ENTITIES))  (LIST (+ (CAR (NTH 1 (NTH I OFFSET_ENTITIES))) (/ (ABS (- (CAR (NTH 1 (NTH (+ I 1) OFFSET_ENTITIES))) (CAR (NTH 1 (NTH I OFFSET_ENTITIES))))) 2)) (- TR_OFFSET_Y 20) 0.0))
  )
  )
  )
  (SETQ I (+ I 1))
  )
)







;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;TABLE FUNCTION;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;


(DEFUN PORTAL_END_POINTS (LIST1 / I ENAME TEMP_ELE LIST2)
  (SETQ I 0)
  (SETQ ENAME NIL)
  (SETQ TEMP_ELE NIL)
  (SETQ LIST2 NIL)
  (WHILE (< I (LENGTH LIST1))
    (SETQ ENAME (NTH I LIST1))
    (SETQ
      TEMP_ELE (SUM_LIST (NTH 1 (ASSOC 3 (YARD_STRUCTURE_INFO ENAME)))
			 (BLOCK_REFERENCE_LENGTHS "PORTAL" ENAME)
	       )
    )
    (SETQ TEMP_ELE (LIST (LIST ENAME (NTH 0 TEMP_ELE))
			 (LIST ENAME (NTH 1 TEMP_ELE))
		   )
    )
    (SETQ LIST2 (CONS TEMP_ELE LIST2))
    (SETQ I (+ I 1))
  )
  (REVERSE LIST2)
)

;;;;;;;;;;;;;;;;;;;;;;;;;;;;;;;;;;;;;;;;;;GENERAL FUNCTIONS;;;;;;;;;;;;;;;;;;;;;;;;;;;;;;;;;;;;;;;;;;;;;;;;;;;;
;;;;;;;;;;;;;;;;;;;;;;;;;;;;;;;;;;;;;;
;;;;;;;;;;;;;;;;;;;;;;SINGLE_ELEMENT FUNCTION;;;;
(DEFUN SINGLE_ELE_LIST (LIST1 POS / N TEMP_ELE LIST2)
  (SETQ N 0)
  (SETQ TEMP_ELE NIL)
  (SETQ LIST2 NIL)
  (WHILE (< N (LENGTH LIST1))
    (SETQ TEMP_ELE (NTH N LIST1))
    (IF	(NOT (ATOM TEMP_ELE))
      (PROGN
	(SETQ TEMP_ELE (NTH POS TEMP_ELE))
	(SETQ LIST2 (CONS TEMP_ELE LIST2))
      )
      (PROGN (SETQ TEMP_ELE TEMP_ELE)
	     (SETQ LIST2 (CONS TEMP_ELE LIST2))
      )
    )
    (SETQ N (+ N 1))
  )
  (SETQ LIST2 (REVERSE LIST2))
)
;;;;;;;;;;;;;;;;;FOR BUILDIING OF LIST;;;;;;;;;;;
(DEFUN BUILD_LIST (LIST1 LIST2 / I J LIST3 TEMP_ELE TEMP_ELE1)
  (SETQ I 0)
  (SETQ LIST3 NIL)
  (WHILE (< I (LENGTH LIST1))
    (SETQ TEMP_ELE (NTH I LIST1))
    (SETQ J 0)
    (SETQ TEMP_ELE1 NIL)
    (WHILE (< J (LENGTH LIST2))
      (SETQ TEMP_ELE1 (CONS (NTH (NTH J LIST2) TEMP_ELE) TEMP_ELE1))
      (SETQ J (+ J 1))
    )
    (SETQ TEMP_ELE1 (REVERSE TEMP_ELE1))
    (SETQ LIST3 (CONS TEMP_ELE1 LIST3))
    (SETQ I (+ I 1))
  )
  (SETQ LIST3 (REVERSE LIST3))
)
;;;;;;;;;;;;;;;;;;;;;FOR ADDING OF TWO LISTS;;;;;
(DEFUN ADD_LISTS (LIST1 LIST2 / I TEMP_ELE MAIN_LIST)
  (SETQ I 0)
  (SETQ MAIN_LIST NIL)
  (WHILE (< I (LENGTH LIST1))
    (IF	(AND (VL-CONSP (NTH I LIST1)) (VL-CONSP (NTH I LIST2)))
      (PROGN (SETQ TEMP_ELE (APPEND (NTH I LIST1) (NTH I LIST2)))
	     (SETQ MAIN_LIST (CONS TEMP_ELE MAIN_LIST))
      )
    )
    (IF	(AND (NOT (VL-CONSP (NTH I LIST1)))
	     (NOT (VL-CONSP (NTH I LIST2)))
	)
      (PROGN (SETQ TEMP_ELE (CONS (NTH I LIST1) (NTH I LIST2)))
	     (SETQ MAIN_LIST (CONS TEMP_ELE MAIN_LIST))
      )
    )
    (IF	(AND (VL-CONSP (NTH I LIST1))
	     (NOT (VL-CONSP (NTH I LIST2)))
	)
      (PROGN (SETQ TEMP_ELE (APPEND (NTH I LIST1) (LIST (NTH I LIST2))))
	     (SETQ MAIN_LIST (CONS TEMP_ELE MAIN_LIST))
      )
    )
    (IF	(AND (NOT (VL-CONSP (NTH I LIST1)))
	     (VL-CONSP (NTH I LIST2))
	)
      (PROGN (SETQ TEMP_ELE (CONS (NTH I LIST1) (NTH I LIST2)))
	     (SETQ MAIN_LIST (CONS TEMP_ELE MAIN_LIST))
      )
    )
    (SETQ I (+ I 1))
  )
  (SETQ MAIN_LIST (REVERSE MAIN_LIST))
)
;;;;;;;;;;;;;;;;;;;;;;;;;;;;;;;;;;;;;
(DEFUN INDEX_ADD (LIST1 / I LIST2)
  (SETQ I 0)
  (SETQ LIST2 NIL)
  (WHILE (< I (LENGTH LIST1))
    (IF	(= (VL-CONSP (NTH I LIST1)) NIL)
      (SETQ LIST2 (CONS (LIST I (NTH I LIST1)) LIST2))
      (SETQ LIST2 (CONS (CONS I (NTH I LIST1)) LIST2))
    )
    (SETQ I (+ I 1))
  )
  (SETQ LIST2 (REVERSE LIST2))
)
;;;;;;;;;;;;;;;;;;;;;;;;;;;;;;;;;;;;;
(DEFUN LIST_FORM (LIST1 / TEMP_LIST I)
  (SETQ TEMP_LIST NIL)
  (SETQ I 0)
  (WHILE (< I (LENGTH LIST1))
    (SETQ TEMP_LIST (APPEND (REVERSE (NTH I LIST1)) TEMP_LIST))
    (SETQ I (+ I 1))
  )
  (SETQ TEMP_LIST (REVERSE TEMP_LIST))
)
;;;;;;;;;;;;;;;;;;;;;;;;;;;;;;;;;;;;;
;;;SPACE_REMOVE IN A GIVEN STRING
(DEFUN SPACE_REMOVE (STR /)
  (IF (OR (= (TYPE STR) 'STR) (= (TYPE STR) 'NIL))
    (PROGN
      (IF (AND (/= STR NIL))
	(VL-LIST->STRING
	  (VL-REMOVE 32 (VL-STRING->LIST STR))
	)
      )
    )
    (PROGN
      (ALERT
	"TO PROGARMMER INPUT IS GOING WRONG WITH  SPACE_REMOVE FUNCTION"
      )
      (QUIT)
    )
  )
)
;;;;;;;;;;;;;;;;;;;;;;;;;;;;;;;;;;;;;
(DEFUN MAP_NEAREST1 (LIST1 PT K / I TEMP_SET LIST2)
  (SETQ I 0)
  (SETQ TEMP_SET NIL)
  (SETQ LIST2 NIL)
  (WHILE (< I (LENGTH LIST1))
    (IF	(NOT (ATOM (NTH K (NTH I LIST1))))
      (PROGN (SETQ TEMP_SET
		    (LIST
		      (ABS (DISTANCE (NTH K (NTH I LIST1)) PT))
		      (NTH I LIST1)
		    )
	     )
	     (SETQ LIST2 (CONS TEMP_SET LIST2))
      )
      (PROGN (SETQ TEMP_SET (LIST (ABS (DISTANCE (NTH I LIST1) PT))
				  (NTH I LIST1)
			    )
	     )
	     (SETQ LIST2 (CONS TEMP_SET LIST2))
      )
    )
    (SETQ I (+ I 1))
  )
  (NTH 1 (NTH 0 (SORT_FUN LIST2 0 0)))
)
;;;;;;;;;;;;;;;;;;;;;;;;;;;;;;;;;;;;;
(DEFUN SORT_FUN	(LIST1 FLAG1 FLAG2 /)
  (IF (= NIL (VL-CONSP (CAR LIST1)))
    (PROGN (SETQ LIST1 (INDEX_ADD LIST1))
	   (SETQ LIST1
		  (VL-SORT LIST1
			   '(LAMBDA (X Y) (< (CADR X) (CADR Y)))
		  )
	   )
	   (SETQ LIST1 (MAPCAR '(LAMBDA (X) (CADR X)) LIST1))
    )
    (PROGN
      (IF (NOT (ATOM (NTH FLAG1 (NTH 0 LIST1))))
	(SETQ LIST1
	       (VL-SORT
		 LIST1
		 '(LAMBDA (X Y)
		    (< (NTH FLAG2 (NTH FLAG1 X)) (NTH FLAG2 (NTH FLAG1 Y)))
		  )
	       )
	)
	(PROGN (SETQ LIST1
		      (VL-SORT LIST1
			       '(LAMBDA (X Y) (< (NTH FLAG2 X) (NTH FLAG2 Y)))
		      )
	       )
	)
      )
    )
  )
  LIST1
)
;;;;;;;;;;;;;;;;;;;;;;;;;;;;;;;;;;;;;
(DEFUN FILTER_LIST (LIST1 LIST2 POSITION / I LOOP_ELE TEMP_ELE LIST3)
  (SETQ I 0)
  (SETQ LIST3 NIL)
  (WHILE (< I (LENGTH LIST2))
    (SETQ LOOP_ELE (NTH POSITION (NTH I LIST2)))
    (IF	(>= (VL-POSITION LOOP_ELE LIST1) 0)
      (PROGN (SETQ TEMP_ELE (NTH I LIST2))
	     (SETQ LIST3 (CONS TEMP_ELE LIST3))
      )
    )
    (SETQ I (+ I 1))
  )
  (SETQ LIST3 (REVERSE LIST3))
)
;;;;;;;;;;;;;;;;;;;;;;;;;;;;;;;;;;;;;
;;;;;;;;;;;;;;;;;;;;;;;;;;;;;;;;;;;;;;;;;;;;;;;;;;;;;;;;;;;;;;;;;;;;;;
;;;;;;;;;;;;;;;LIST1 IS INPUT LIST PATTERN (()()()) AND K IS STRING POSITION
  (DEFUN STRING_SORT (LIST1 K / LIST2 ASCII_SUM I J TEMP_ELE NEW_ELE)
    (SETQ I 0)
    (SETQ LIST2 NIL)
    (WHILE (< I (LENGTH LIST1))
      (SETQ J 1)
      (SETQ TEMP_ELE (NTH K (NTH I LIST1)))
      (SETQ ASCII_SUM 0)
      (WHILE (<= J (STRLEN TEMP_ELE))
	(SETQ ASCII_SUM (+ ASCII_SUM (ASCII (SUBSTR TEMP_ELE J 1))))
	(SETQ J (+ J 1))
      )
      (SETQ NEW_ELE (CONS ASCII_SUM (NTH I LIST1)))
      (SETQ LIST2 (CONS NEW_ELE LIST2))
      (SETQ I (+ I 1))
    )
    (SETQ LIST2 (SORT_FUN LIST2 0 0))
    (SETQ LIST2 (MAPCAR '(LAMBDA (X) (CDR X)) LIST2))
  )
;;;;;;;;;;;;;;;;;;;;;;;;;;;;;;;;;;;;;;;;;;;;;;;;;;;;;;;;;;;;;;;;;;;;;;;;;;;;;
;;;;;;;;;;;;;;;;;;;;;;;;;;;;;;;;;;;;
;;;TO CREATE LIST OF LENGTH LEN
(DEFUN N_ELE_LIST (XYZ LEN / I)
  (SETQ I 0)
  (SETQ ELE_LIST NIL)
  (WHILE (< I LEN)
    (SETQ ELE_LIST (CONS XYZ ELE_LIST))
    (SETQ I (+ I 1))
  )
  (SETQ ELE_LIST (REVERSE ELE_LIST))
)
;;;;;;;;;;;;;;;;;;;;;;;;;;;;;;;;;;;;;;
;;;;;REPLACE ONE ELEMENT IN THE AT PARTICULA POSITION IN LIST
(DEFUN REPLACE_ELE_POS (LIST1 ELE POS / I LIST2)
  (SETQ I 0)
  (SETQ LIST2 NIL)
  (WHILE (< I (LENGTH LIST1))
    (SETQ TEMP_ELE (NTH I LIST1))
    (IF	(= I POS)
      (SETQ LIST2 (CONS ELE LIST2))
      (SETQ LIST2 (CONS TEMP_ELE LIST2))
    )
    (SETQ I (+ I 1))
  )
  (SETQ LIST2 (REVERSE LIST2))
)
;;;;;;;;;;;;;;;;;;;;;;;;;;;;;;;;;;;;;;
;;;;;;;;;;;TO FIND ROW COLUMN OF GIVEN EXCEL TYPE STRING 
(DEFUN ROW_COL (STR /)
;;;;;;;;;;;;;;;;;;;;INTERNAL FUNCTIONS
  (DEFUN STR_BREAK (STR / I J)
    (SETQ STR (VL-STRING->LIST (STRCASE STR)))
    (SETQ I 0)
    (WHILE (< I (LENGTH STR))
      (IF (AND (>= (NTH I STR) 65) (<= (NTH I STR) 90))
	(PROGN (SETQ I (+ I 1)))
	(PROGN (SETQ J I) (SETQ I (LENGTH STR)))
      )
    )
    (SETQ J (+ J 1))
  )
  (DEFUN ATON (STR /)
    (- (ASCII (STRCASE (SUBSTR STR 1 1))) 64)
  )
  (DEFUN EXCEL_ALPA (STR / I SUM)
    (SETQ STR (VL-LIST->STRING (REVERSE (VL-STRING->LIST STR))))
    (SETQ I 0)
    (SETQ SUM 0)
    (WHILE (< I (STRLEN STR))
      (SETQ SUM (+ SUM (* (ATON (SUBSTR STR (+ I 1) 1)) (EXPT 26 I))))
      (SETQ I (+ I 1))
    )
    SUM
  )
;;;;;;;;;;;;;;;;;;;;INTERNAL FUNCTIONS END
;;;;;;MAIN PROGRAM FOR ROW_COL START
  (SETQ STR (SPACE_REMOVE STR))
  (LIST	(- (ATOI (SUBSTR STR (STR_BREAK STR))) 1)
	(- (EXCEL_ALPA (SUBSTR STR 1 (- (STR_BREAK STR) 1))) 1)
  )
;;;;;;;;;MAIN PROGRAM FOR ROW_COL END
)
;;;;;;;;;;;;;;;;;;;;;;;;;;;;;;;;;;;;;;;;;;;;;;;;;;;;;;;;;;;;;;;;;;;;;;;;;;
;;;;;;;;;;;;;;;;;;;;;;;;;;;;;;;;;;PRINTING SUB MODULE;;;;;;;;;;;;;;;;;;;;;;;;;;;;;;;;;;;;;;;;;;;;;;;
;;;;;;;;INPUTS DISCRIPTION TBL--->TABLE OBJECT
;;;;;;;;;;;;;;;;;;;;;;;;;;DATA--->DATA TO PRINT EXAMPLE:(()())
;;;;;;;;;;;;;DATA WHICH IS NOT GOING TO PRINT IS REPRESENT AS ""
;;;;;;;;;;;;;;;;;;;;;;;;;;EMPTY--->EMPTY ROW FROM WHICH PRINTING HAS TO BE START
;;;;;;;;;;;;;;;;;;;;;;;;;;ROW_WIDTH--->ROW WIDTH 
;;;;IT IS VERTICAL PRINTING FUNCTION
(DEFUN TBL_PRINT
       (TBL DATA EMPTY_ROW ROW_WIDTH / ST_ROW PRESENT_ROW I J)
  (SETQ I 0)
  (SETQ ST_ROW EMPTY_ROW)
  (SETQ TBL (VLAX-ENAME->VLA-OBJECT TBL))
;;;;;;;;ST_ROW MAKING
  (WHILE (< I (LENGTH DATA))
    (SETQ PRESENT_ROW (+ I ST_ROW))
    (VLAX-INVOKE-METHOD
      TBL "INSERTROWS" PRESENT_ROW ROW_WIDTH 1)
    (SETQ J 0)
;;;;ADDING ROW FOR PRINTING
;;;;PRINTING DATA
    (WHILE (< J (LENGTH (NTH I DATA)))
      (IF (/= "" (NTH J (NTH I DATA)))
	(PROGN
	  (VLAX-INVOKE-METHOD
	    TBL
	    "SETCELLVALUE"
	    PRESENT_ROW
	    J
	    (NTH J (NTH I DATA))
	  )
	  (SETQ J (+ J 1))
	)
	(SETQ J (+ J 1))
      )
    )
    (SETQ I (+ I 1))
  )
  (PRINC)
)
;;;;;;;;;;;;;;;;;;;;;;;;;;;;;;;;;;;;;;;;;;;;;;;;;;;;;;;;;;;;;;;;;;;;;;;;;;;;;;;
;;;;;;;FINDING OF EFFECTIVE NAME;;;;;;;;;;;;;;;;;;;;;;;;;;;;;;;;;;;;;;;;;;;;;;;
(DEFUN EFFECTIVE_NAME (ENAME /)
  (VLAX-GET-PROPERTY
    (VLAX-ENAME->VLA-OBJECT ENAME)
    "EFFECTIVENAME"
  )
)
;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;;;;;;;;GENERAL FUNCTIONS END;;;;;;;;;;;;;;;;;;;;;;;;;;;;;;;



 ;_________________________________________FUNCTION FOR MAPPING ANCHORS WITH MASTS, PORTAL AND TTC'S_________________________________________________________________________________;
 ;__________________________________INPUT---> TWO POINTS ON THE SCREEN______________________________________________________________________________________________________________________;
 ;_________________________OUTPUT IS ANCHOR_STRUCTURE_MAP_DATA---> LIST PATTERN==> '((STRUCTURE_ENTITY1,ANCHOR_ENTITY1)(STRUCTURE_ENTITY2,ANCHOR_ENTITY2)...............))   _______________;
(DEFUN ANCHOR_STRUCTURE_MAPPING	(/
				 WPT1
				 WPT2
				 MAST_TTC
				 PORTAL_ENTITIES
				 PORTAL_ENDS
				 PORTAL_END_UP
				 PORTAL_END_DN
				 PORTAL_END_UP_DN
				 MAST_PORTAL_TTC
				 ANCHOR_LIST
				 ANCHOR_STRUCTURE_MAP_DATA
				)
  (SETQ WPT1 (GETPOINT "ENTER STARTING POINT IN LOP"))
  (SETQ WPT2 (GETPOINT "\n ENTER ENDING POINT IN LOP"))
  (SETQ	MAST_ENTITIES
	 (YARD_DATA_COLLECT
	   WPT1
	   WPT2
	   '("SINGLE_CANT_MAST"			 "DOUBLE_CANT_MAST"
	     "TRIPLE_CANT_MAST"			 "TTC"
	     "SS1"	       "SS2"		 "SS3"
	     "SS4"
	    )
	   1
	   5
	 )
  )
  (SETQ UPLINE_MAST_ENTITIES (FILTER_LIST '("DN") MAST_ENTITIES 1))
  (SETQ DNLINE_MAST_ENTITIES (FILTER_LIST '("UP") MAST_ENTITIES 1))
  (SETQ	UPLINE_MAST_ENTITIES
	 (EXTRACT_ENTITY_INFO
	   (SINGLE_ELE_LIST UPLINE_MAST_ENTITIES 0)
	   1
	   3
	 )
  )
  (SETQ	DNLINE_MAST_ENTITIES
	 (EXTRACT_ENTITY_INFO
	   (SINGLE_ELE_LIST DNLINE_MAST_ENTITIES 0)
	   1
	   3
	 )
  )
  (SETQ	PORTAL_ENTITIES
	 (YARD_DATA_COLLECT WPT1 WPT2 '("PORTAL" "SS5") 1 3)
  )
  (SETQ TTC_ENTITIES (YARD_DATA_COLLECT WPT1 WPT2 '("TTC" "SS4") 1 3))
  (SETQ BUFFER_END_ENTITIES (YARD_DATA_COLLECT WPT1 WPT2 '("SS0") 1 3))

  ;;***************NEWLY ADDED********************************************************************************************************************;--->START
					;(SETQ MAST_ENTITIES (YARD_DATA_COLLECT WPT1 WPT2 '("SINGLE_CANT_MAST" "DOUBLE_CANT_MAST" "TRIPLE_CANT_MAST" "TTC" "SS0" "SS1" "SS2" "SS3" "SS4") 1 3))
					;(SETQ PORTAL_ENTITIES (YARD_DATA_COLLECT WPT1 WPT2 '("PORTAL" "SS5") 1 3))
					;(SETQ PORTAL_ENDS (PORTAL_END_POINTS (SINGLE_ELE_LIST PORTAL_ENTITIES 0)))
					;(SETQ PORTAL_END_UP (SINGLE_ELE_LIST PORTAL_ENDS 0))
					;(SETQ PORTAL_END_DN (SINGLE_ELE_LIST PORTAL_ENDS 1))
					;(SETQ PORTAL_END_UP_DN (BUILD_LIST (ADD_LISTS PORTAL_END_UP PORTAL_END_DN) '(0 1 3)))
					;(SETQ MAST_WITH_LOC_NO (BUILD_LIST (ATTRIBUTES_FROM_ENTITIES MAST_ENTITIES "MAST_NUMBER1" 0) '(2 0 1)))
					;(SETQ PORTAL_WITH_LOC_NO (BUILD_LIST (ATTRIBUTES_FROM_ENTITIES PORTAL_END_UP_DN "MAST_NUMBER1" 0) '(3 0 1 2)) )
					;(SETQ WITH_LOC_NO (APPEND MAST_WITH_LOC_NO PORTAL_WITH_LOC_NO))
					;(SETQ WITH_LOC_NO (SORT_FUN WITH_LOC_NO 0 0))
					;(SETQ TOTAL_STRUCTURE_ENTITIES (REMOVE_NTH_ELE WITH_LOC_NO 0))
  ;;***************NEWLY ADDED********************************************************************************************************************;--->END

  (SETQ	CANTI_LIST
	 (YARD_DATA_COLLECT
	   WPT1
	   WPT2
	   '("SINGLE_CANT_MAST"	    "SINGLE_CANT_DA"
	     "DOUBLE_CANT_MAST"	    "DOUBLE_CANT_DA"
	     "TRIPLE_CANT_MAST"	    "TRIPLE_CANT_DA"
	     "SINGLE_CANT_UPRIGHT"  "DOUBLE_CANT_UPRIGHT"
	     "TRIPLE_CANT_UPRIGHT"  "SS0"
	     "SS1"		    "SS2"
	     "SS3"		    "BOX_TYPE"
	    )
	   1
	   3
	 )
  )
  (SETQ	MAST_TTC (YARD_DATA_COLLECT
		   WPT1
		   WPT2
		   '("SINGLE_CANT_MAST"
		     "DOUBLE_CANT_MAST"
		     "TRIPLE_CANT_MAST"		       "TTC"
		     "SS0"	      "SS1"	       "SS2"
		     "SS3"	      "SS4"
		    )
		   1
		   3
		 )
  )
  (SETQ	MAST_E (YARD_DATA_COLLECT
		 WPT1
		 WPT2
		 '("SINGLE_CANT_MAST" "DOUBLE_CANT_MAST"
		   "TRIPLE_CANT_MAST" "SS0"
		   "SS1"	      "SS2"
		   "SS3"
		  )
		 1
		 3
	       )
  )
  (SETQ	PORTAL_ENDS
	 (PORTAL_END_POINTS (SINGLE_ELE_LIST PORTAL_ENTITIES 0))
  )
  (SETQ PORTAL_END_UP (SINGLE_ELE_LIST PORTAL_ENDS 0))
  (SETQ PORTAL_END_DN (SINGLE_ELE_LIST PORTAL_ENDS 1))
  (SETQ	PORTAL_END_UP_DN
	 (BUILD_LIST
	   (ADD_LISTS PORTAL_END_UP PORTAL_END_DN)
	   '(0 1 3)
	 )
  )
  (SETQ MAST_PORTAL_TTC (APPEND MAST_TTC PORTAL_END_UP PORTAL_END_DN))
  (SETQ	ANCHOR_LIST
	 (YARD_DATA_COLLECT WPT1 WPT2 '("ANCHOR" "BTB_ANC") 1 3)
  )
  (SETQ	ANCHOR_STRUCTURE_MAP_DATA
	 (DATA_TO_STRUCTURE_MAP1
	   ANCHOR_LIST
	   MAST_PORTAL_TTC
	   1
	   1
	 )
  )
  (SETQ	ANCHOR_STRUCTURE_MAP_DATA
	 (BUILD_LIST
	   ANCHOR_STRUCTURE_MAP_DATA
	   '(1 0)
	 )
  )
)
 ;_____________________________________________________________END__________________________________________________________________________________________________________________________;


;;;;;;;;;;;;;;;;;;;;;;;;;;;;;;;;;;;;;;;;;;;;;;;;;;;;;;;;;;;;;;;;;;;;;;;;;;;;;;;;;;;;;;;;;;;;;;;;;;;;;;;;;;;;;;;;;;;;
(DEFUN C:TABLE_FUN (/		TBL	    I		MAIN_LIST3
		    MAIN_LIST4	MAIN_LIST1  MAIN_LIST	MAIN_LIST2
		    EMPTY1	EMPTY2	    EMPTY3	EMPTY4
		    ROW_WIDTH	LIST1	    TENSION_MUL
		   )
;;;;;;;;;;;;;;;;;;;;;SUB_FUNCTION_MODULES_START;;;;;;;;;;;;;;;;;;;;;;;;;;;;;;;;;;;;;;;;;;;;;;;;;;;;;;;;;;;;;;;;;;;;;;
;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;;;;;;;;;MAST AND ANCHOR TAG RETERIVAL FUNCTION;;;;;;;;;;;;;;;;;;;;;
  (DEFUN MAST_ANC_TAG (ST ANC_ST / TEMP_ELE FLAG)
;;;;;;;;;;;;;;;;;;;;;;;;;;;;;;;;;;;;;;;;;;;;;;;;;;
    (DEFUN STR_BREAK (STR / TEMP_ELE)
      (IF (/= NIL
	      (SETQ TEMP_ELE (VL-STRING-POSITION (ASCII "/") STR))
	  )
	(SUBSTR STR (+ 2 TEMP_ELE))
	(PROGN
	  (IF (/= NIL
		  (SETQ TEMP_ELE (VL-STRING-POSITION (ASCII "\\") STR))
	      )
	    (SUBSTR STR (+ 2 TEMP_ELE))
	    NIL
	  )
	)
      )
    )
;;;;;;;;;;;;;;;;;;;;;;;;;;;;;;;;;;;;;;;;;;;;;;;;;;;
    (DEFUN ANCHOR_STR_MAKE (STR /)
      (SETQ STR (SPACE_REMOVE STR))
      (SUBSTR STR 1 (VL-STRING-POSITION (ASCII "(") STR))
    )
;;;;;;;;;;;;;;;;;;;;;;;;;;;;;;;;;;;;;;;;;;;;;;;;;;
    (DEFUN SERIAL_NO (STR /)
      (SETQ STR (SPACE_REMOVE STR))
      (IF (/= STR "")
	(SUBSTR STR (+ 2 (VL-STRING-POSITION (ASCII "-") STR)))
	" "
      )
    )
;;;;;;;;;;;;;;;;;;;;;;;;;;;;;;;;;;;;;;;;;;;;;;;;;;
;;;IN THIS FLAG 0 OR 1 IS ALLOWED;;THIS FUNCTION IS FOR BTB_ANCHOR ONLY
    (DEFUN BTB_WIRE_ADJUST (BTB_DATA FLAG /)
      (LIST
	(NTH
	  1
	  (NTH
	    FLAG
	    (SORT_FUN (FILTER_LIST '("WIRE_NO1" "WIRE_NO2") BTB_DATA 0)
		      2
		      0
	    )
	  )
	)
	(NTH
	  1
	  (NTH
	    FLAG
	    (SORT_FUN
	      (FILTER_LIST '("ANCHOR_TYPE1" "ANCHOR_TYPE2") BTB_DATA 0)
	      2
	      0
	    )
	  )
	)
      )
    )
;;;;;;;;;;;;;;;;;;;;;;;;;;;;;;;;;;;;;;;;;;;;;;;;;;;
    (DEFUN ANC_FLAG (ST ANC_ST / FLAG TEMP_LIST TEMP_PT)
      (IF
	(= "PORTAL" (EFFECTIVE_NAME ST))
	 (PROGN	(SETQ
		  TEMP_LIST (SORT_FUN (LIST_FORM (SUB_ENT_DATA_COLLECT
						   ST
						   '((0 . "LINE"))
						   10
						   11
						 )
				      )
				      0
				      1
			    )
		)
		(SETQ TEMP_PT
		       (MAP_NEAREST1 TEMP_LIST (CDR (ASSOC 10 (ENTGET ANC_ST))) 0)
		)
		(IF (= 0 (VL-POSITION TEMP_PT TEMP_LIST))
		  (SETQ FLAG 1)
		  (SETQ FLAG 0)
		)
	 )
	 (PROGN
	   (SETQ FLAG 0)
	 )
      )
    )
;;;;;;;;;;;;;;;;;;;;;;;;;;;;;;;;;;;;;;;;;;;;;;;;;;;
;;;;;;;SUB MAIN
;;;;;;;;;;;;;;;;;;;;;;;;;;;;;;;;;;;;;;;;;;;;;;;;;;;;;;;;;;;;;;;;;;;;;;;;;;;;;;;;;;;;;;;;;;;;;;;;;;;;;;;;    
;;;;;;;;;;;;;;;;;;;;;;;;;;;;;;;;;;;;;;;;;;;;;;;;;;
    (SETQ TEMP_ELE (CADR (ASSOC 4 (YARD_STRUCTURE_INFO ST))))
    (SETQ TEMP_ELE1 (CADR (ASSOC 4 (YARD_STRUCTURE_INFO ANC_ST))))
    (SETQ FLAG (ANC_FLAG ST ANC_ST))
    (IF	(= "ANCHOR" (EFFECTIVE_NAME ANC_ST))
      (PROGN
	(IF (= "PORTAL" (EFFECTIVE_NAME ST))
	  (PROGN
	    (IF	(= FLAG 0)
	      (PROGN
		(LIST
		  (LIST
		    (SERIAL_NO (CADR (ASSOC "WIRE_RUN1" TEMP_ELE1)))
		    (CADR (ASSOC "WIRE_RUN1" TEMP_ELE1))
		    (CADR (CAR (FILTER_LIST
				 '("MAST_NUMBER1" "SS_NUMBER1")
				 TEMP_ELE
				 0
			       )
			  )
		    )
		    (STR_BREAK (CADR (CAR (FILTER_LIST
					    '("CHAINAGE1" "SS_CHAINAGE1")
					    TEMP_ELE
					    0
					  )
				     )
			       )
		    )
		    (ANCHOR_STR_MAKE
		      (CADR (ASSOC "ANCHOR_TYPE1" TEMP_ELE1))
		    )
		    (CADR (ASSOC 3 (YARD_STRUCTURE_INFO ST)))
		    (CADR (ASSOC 5 (YARD_STRUCTURE_INFO ANC_ST)))
		  )
		)
	      )
;;;;;;ANCHOR PROGN FOR PORTALS FOR TOP
	      (PROGN
		(LIST (LIST
			(SERIAL_NO (CADR (ASSOC "WIRE_RUN1" TEMP_ELE1)))
			(CADR (ASSOC "WIRE_RUN1" TEMP_ELE1))
			(CADR (ASSOC "MAST_NUMBER2" TEMP_ELE))
			(STR_BREAK (CADR (ASSOC "CHAINAGE2" TEMP_ELE)))
			(ANCHOR_STR_MAKE
			  (CADR (ASSOC "ANCHOR_TYPE1" TEMP_ELE1))
			)
			(CADR (ASSOC 3 (YARD_STRUCTURE_INFO ST)))
			(CADR (ASSOC 5 (YARD_STRUCTURE_INFO ANC_ST)))
		      )
		)
	      )
;;;;;;;ANCHOR PROGN FOR PORTALS FOR BOTTOM
	    )
	  )
;;;;;;ANCHOR PROGN FOR PORTALS END
	  (PROGN
	    (LIST
	      (LIST
		(SERIAL_NO (CADR (ASSOC "WIRE_RUN1" TEMP_ELE1)))
		(CADR (ASSOC "WIRE_RUN1" TEMP_ELE1))
		(CADR (CAR (FILTER_LIST
			     '("MAST_NUMBER1" "SS_NUMBER1")
			     TEMP_ELE
			     0
			   )
		      )
		)
		(STR_BREAK (CADR (CAR (FILTER_LIST
					'("CHAINAGE1" "SS_CHAINAGE1")
					TEMP_ELE
					0
				      )
				 )
			   )
		)
		(ANCHOR_STR_MAKE
		  (CADR (ASSOC "ANCHOR_TYPE1" TEMP_ELE1))
		)
		(CADR (ASSOC 3 (YARD_STRUCTURE_INFO ST)))
		(CADR (ASSOC 5 (YARD_STRUCTURE_INFO ANC_ST)))
	      )
	    )
	  )
;;;;ANCHOR PROGN FOR MASTS END
	)
      )
;;;PROGN FOR ANCHOR PROGN END
;;;;;;;;;;;;;PROGN FOR BACK TO BACK TO ANCHOR
      (PROGN
	(IF (= (EFFECTIVE_NAME ST) "PORTAL")
	  (PROGN
	    (IF	(= FLAG 0)
	      (PROGN
		(LIST
		  (LIST
		    (SERIAL_NO (CAR (BTB_WIRE_ADJUST TEMP_ELE1 0)))
		    (CAR (BTB_WIRE_ADJUST TEMP_ELE1 0))
		    (CADR (CAR (FILTER_LIST
				 '("MAST_NUMBER1" "SS_NUMBER1")
				 TEMP_ELE
				 0
			       )
			  )
		    )
		    (STR_BREAK (CADR (CAR (FILTER_LIST
					    '("CHAINAGE1" "SS_CHAINAGE1")
					    TEMP_ELE
					    0
					  )
				     )
			       )
		    )
		    (ANCHOR_STR_MAKE
		      (CADR (BTB_WIRE_ADJUST TEMP_ELE1 0))
		    )
		    (CADR (ASSOC 3 (YARD_STRUCTURE_INFO ST)))
		    "START"
		  )
		  (LIST
		    (SERIAL_NO (CAR (BTB_WIRE_ADJUST TEMP_ELE1 1)))
		    (CAR (BTB_WIRE_ADJUST TEMP_ELE1 1))
		    (CADR (CAR (FILTER_LIST
				 '("MAST_NUMBER1" "SS_NUMBER1")
				 TEMP_ELE
				 0
			       )
			  )
		    )
		    (STR_BREAK (CADR (CAR (FILTER_LIST
					    '("CHAINAGE1" "SS_CHAINAGE1")
					    TEMP_ELE
					    0
					  )
				     )
			       )
		    )
		    (ANCHOR_STR_MAKE
		      (CADR (BTB_WIRE_ADJUST TEMP_ELE1 1))
		    )
		    (CADR (ASSOC 3 (YARD_STRUCTURE_INFO ST)))
		    "END"
		  )
		)
	      )
;;;TRUE PROGN END
	      (PROGN
		(LIST
		  (LIST	(SERIAL_NO (CAR (BTB_WIRE_ADJUST TEMP_ELE1 0)))
			(CAR (BTB_WIRE_ADJUST TEMP_ELE1 0))
			(CADR (ASSOC "MAST_NUMBER2" TEMP_ELE))
			(STR_BREAK (CADR (ASSOC "CHAINAGE2" TEMP_ELE)))
			(ANCHOR_STR_MAKE
			  (CADR (BTB_WIRE_ADJUST TEMP_ELE1 0))
			)
			(CADR (ASSOC 3 (YARD_STRUCTURE_INFO ST)))
			"START"
		  )
		  (LIST	(SERIAL_NO (CAR (BTB_WIRE_ADJUST TEMP_ELE1 1)))
			(CAR (BTB_WIRE_ADJUST TEMP_ELE1 1))
			(CADR (ASSOC "MAST_NUMBER2" TEMP_ELE))
			(STR_BREAK (CADR (ASSOC "CHAINAGE2" TEMP_ELE)))
			(ANCHOR_STR_MAKE
			  (CADR (BTB_WIRE_ADJUST TEMP_ELE1 1))
			)
			(CADR (ASSOC 3 (YARD_STRUCTURE_INFO ST)))
			"END"
		  )
		)
	      )
	    )
	  )
	  (PROGN
	    (LIST
	      (LIST (SERIAL_NO (CAR (BTB_WIRE_ADJUST TEMP_ELE1 0)))
		    (CAR (BTB_WIRE_ADJUST TEMP_ELE1 0))
		    (CADR (CAR (FILTER_LIST
				 '("MAST_NUMBER1" "SS_NUMBER1")
				 TEMP_ELE
				 0
			       )
			  )
		    )
		    (STR_BREAK (CADR (CAR (FILTER_LIST
					    '("CHAINAGE1" "SS_CHAINAGE1")
					    TEMP_ELE
					    0
					  )
				     )
			       )
		    )
		    (ANCHOR_STR_MAKE
		      (CADR (BTB_WIRE_ADJUST TEMP_ELE1 0))
		    )
		    (CADR (ASSOC 3 (YARD_STRUCTURE_INFO ST)))
		    "START"
	      )
	      (LIST (SERIAL_NO (CAR (BTB_WIRE_ADJUST TEMP_ELE1 1)))
		    (CAR (BTB_WIRE_ADJUST TEMP_ELE1 1))
		    (CADR (CAR (FILTER_LIST
				 '("MAST_NUMBER1" "SS_NUMBER1")
				 TEMP_ELE
				 0
			       )
			  )
		    )
		    (STR_BREAK (CADR (CAR (FILTER_LIST
					    '("CHAINAGE1" "SS_CHAINAGE1")
					    TEMP_ELE
					    0
					  )
				     )
			       )
		    )
		    (ANCHOR_STR_MAKE
		      (CADR (BTB_WIRE_ADJUST TEMP_ELE1 1))
		    )
		    (CADR (ASSOC 3 (YARD_STRUCTURE_INFO ST)))
		    "END"
	      )
	    )
	  )
	)
      )
    )
;;;TOATAL IF END
  )
;;;;;;;;;;;;;;;;;;;;;;;;;;;;;;;;;;;;;;;;;;;;;;;;;;;;;;;;;;;;;;;;;;;;;;;;;;;;;;;;;;;;;;;;;;;;;;;;;;;;
  ;;LIST1 IS LIBARAY
;;;;LIST2 IS SPECIFIC TO REQUIREMENT
  (DEFUN DATA_ADJUSTMENT (LIST2	TENSION_MUL	/
				MAIN_LIST	LIST1
				LEN		S.NO
				LOC_NO_ST	CHAINAGE_ST
				ANCHOR_ST	LOC_NO_END
				CHAINAGE_END	ANCHOR_END
				CAT_WIRE	CON_WIRE
				AC_WIRE		LS_WIRE
				FEEDER_WIRE	AEW_WIRE
				ELE_LINK_BWA2	ELE_LINK_ACA2
				ELE_LINK_FA2	ELE_LINK_AEWA2
				ELE_LINK_BWA1	ELE_LINK_ACA1
				ELE_LINK_FA1	ELE_LINK_AEWA1
			       )
;;;;;;;;;;;;;;;;;;;;;;;;;;;;;;;;;;;;;;;;;;;;;;;;;;;;;;;;;;;;;;;;;;;;;;;;;;
    (SETQ LIST1	(LIST (SETQ S.NO "A3")
		      (SETQ LOC_NO_ST "B3")
		      (SETQ CHAINAGE_ST "C3")
		      (SETQ ANCHOR_ST "D3")
		      (SETQ LOC_NO_END "E3")
		      (SETQ CHAINAGE_END "F3")
		      (SETQ ANCHOR_END "G3")
		      (SETQ CAT_WIRE "H3")
		      (SETQ CON_WIRE "I3")
		      (SETQ AC_WIRE "J3")
		      (SETQ LS_WIRE "K3")
		      (SETQ FEEDER_WIRE "L3")
		      (SETQ AEW_WIRE "M3")
		)
    )
    (SETQ LEN (LENGTH LIST1))
;;;;;;;;;;;;;;;;;;;;;;;;;;;;;;;;;;;;;;;;;;;;;;;;;;;;;;;;;;;;;;;;;;;;;;;;;;
;;;;;;;;;;;;;;;;;;;;;;;;;;;;SUB_FUNCTIONS;;;;;;;;;;;;;;;;;;;;;;;;;;;;;;;;;
;;;;;;;;;;;;;;;;;;;;;;;;;;;;;;;;;;;;;;;;;;;;;;;;;;;;;;;;;;;
;;;;;;;TO CALCULATE TENSION LENGTH BETWEEN TO ANCHOR POINTS
    (DEFUN TENSION_EVAL	(LIST1 TENSION_MUL /)
      (RTOS
	(/ (ABS
	     (- (CAR (NTH 5 (NTH 0 LIST1))) (CAR (NTH 5 (NTH 1 LIST1))))
	   )
	   TENSION_MUL
	)
	2
	2
      )
    )
;;;;;;LIST1 IS MAPPED LIST AND ;;;;LEN IS LEN OF LSIT TO FORM
    (DEFUN LIST_ADJUSTMENT (LIST1 LEN / I MAIN_LIST)
      (SETQ I 0)
      (SETQ MAIN_LIST (N_ELE_LIST "" LEN))
      (WHILE (< I (LENGTH LIST1))
	(SETQ MAIN_LIST
	       (REPLACE_ELE_POS
		 MAIN_LIST
		 (CADR (NTH I LIST1))
		 (CADR (ROW_COL (CAR (NTH I LIST1))))
	       )
	)
	(SETQ I (+ I 1))
      )
      MAIN_LIST
    )
;;;;;;;;;;;;;;;;;;;;;;;;;;;;;;;;;;;;;;;;;;;;;;;;;;;;;;;;;;;;;;
;;;;;;;;;;;;;;;;;;;;;;;;;;;;;;;;;;;;;;;;;;;;;;;;;;;;;;;;;;;;; 
;;;;;;;;;;;;;;;;;;;;;;;;;;;SUB FUNCTIONS END;;;;;;;;;;;;;;;;;;;;;;;;;;;;;;
;;;;;;;;;;;;;;;;;;;;;MAIN PROGRAM IN DATA_ADJUSUMENT STARTS;;;;;;;;;;;;;;;;;;;;;;;;;;;;;
    (IF	(= 2 (LENGTH LIST2))
      (PROGN
	(IF (FILTER_LIST '("BWA" "FTA") LIST2 4)
	  (PROGN
	    (SETQ ELE_LINK_BWA2
		   (LIST (LIST S.NO (NTH 1 (NTH 0 LIST2)))
			 (LIST LOC_NO_ST (NTH 2 (NTH 0 LIST2)))
			 (LIST CHAINAGE_ST (NTH 3 (NTH 0 LIST2)))
			 (LIST ANCHOR_ST (NTH 4 (NTH 0 LIST2)))
			 (LIST LOC_NO_END (NTH 2 (NTH 1 LIST2)))
			 (LIST CHAINAGE_END (NTH 3 (NTH 1 LIST2)))
			 (LIST ANCHOR_END (NTH 4 (NTH 1 LIST2)))
			 (LIST CAT_WIRE (TENSION_EVAL LIST2 TENSION_MUL))
			 (LIST CON_WIRE (TENSION_EVAL LIST2 TENSION_MUL))
		   )
	    )
	    (SETQ MAIN_LIST (LIST_ADJUSTMENT ELE_LINK_BWA2 LEN))
	  )
	)
	(IF (FILTER_LIST '("ACA") LIST2 4)
	  (PROGN
	    (SETQ ELE_LINK_ACA2
		   (LIST (LIST S.NO (NTH 1 (NTH 0 LIST2)))
			 (LIST LOC_NO_ST (NTH 2 (NTH 0 LIST2)))
			 (LIST CHAINAGE_ST (NTH 3 (NTH 0 LIST2)))
			 (LIST ANCHOR_ST (NTH 4 (NTH 0 LIST2)))
			 (LIST LOC_NO_END (NTH 2 (NTH 1 LIST2)))
			 (LIST CHAINAGE_END (NTH 3 (NTH 1 LIST2)))
			 (LIST ANCHOR_END (NTH 4 (NTH 1 LIST2)))
			 (LIST AC_WIRE (TENSION_EVAL LIST2 TENSION_MUL))
		   )
	    )
	    (SETQ MAIN_LIST (LIST_ADJUSTMENT ELE_LINK_ACA2 LEN))
	  )
	)
	(IF (FILTER_LIST '("FA") LIST2 4)
	  (PROGN
	    (SETQ ELE_LINK_FA2
		   (LIST (LIST S.NO (NTH 1 (NTH 0 LIST2)))
			 (LIST LOC_NO_ST (NTH 2 (NTH 0 LIST2)))
			 (LIST CHAINAGE_ST (NTH 3 (NTH 0 LIST2)))
			 (LIST ANCHOR_ST (NTH 4 (NTH 0 LIST2)))
			 (LIST LOC_NO_END (NTH 2 (NTH 1 LIST2)))
			 (LIST CHAINAGE_END (NTH 3 (NTH 1 LIST2)))
			 (LIST ANCHOR_END (NTH 4 (NTH 1 LIST2)))
			 (LIST FEEDER_WIRE (TENSION_EVAL LIST2 TENSION_MUL))
		   )
	    )
	    (SETQ MAIN_LIST (LIST_ADJUSTMENT ELE_LINK_FA2 LEN))
	  )
	)
	(IF (FILTER_LIST '("AEWA") LIST2 4)
	  (PROGN
	    (SETQ ELE_LINK_AEWA2
		   (LIST (LIST S.NO (NTH 1 (NTH 0 LIST2)))
			 (LIST LOC_NO_ST (NTH 2 (NTH 0 LIST2)))
			 (LIST CHAINAGE_ST (NTH 3 (NTH 0 LIST2)))
			 (LIST ANCHOR_ST (NTH 4 (NTH 0 LIST2)))
			 (LIST LOC_NO_END (NTH 2 (NTH 1 LIST2)))
			 (LIST CHAINAGE_END (NTH 3 (NTH 1 LIST2)))
			 (LIST ANCHOR_END (NTH 4 (NTH 1 LIST2)))
			 (LIST AEW_WIRE (TENSION_EVAL LIST2 TENSION_MUL))
		   )
	    )
	    (SETQ MAIN_LIST (LIST_ADJUSTMENT ELE_LINK_AEWA2 LEN))
	  )
	)
      )
    )
    (IF	(= 1 (LENGTH LIST2))
      (PROGN
	(IF (FILTER_LIST '("BWA" "FTA") LIST2 4)
	  (PROGN
	    (SETQ ELE_LINK_BWA1
		   (LIST (LIST S.NO (NTH 1 (NTH 0 LIST2)))
			 (LIST LOC_NO_ST (NTH 2 (NTH 0 LIST2)))
			 (LIST CHAINAGE_ST (NTH 3 (NTH 0 LIST2)))
			 (LIST ANCHOR_ST (NTH 4 (NTH 0 LIST2)))
		   )
	    )
	    (SETQ MAIN_LIST (LIST_ADJUSTMENT ELE_LINK_BWA1 LEN))
	  )
	)
	(IF (FILTER_LIST '("ACA") LIST2 4)
	  (PROGN
	    (SETQ ELE_LINK_ACA1
		   (LIST (LIST S.NO (NTH 1 (NTH 0 LIST2)))
			 (LIST LOC_NO_ST (NTH 2 (NTH 0 LIST2)))
			 (LIST CHAINAGE_ST (NTH 3 (NTH 0 LIST2)))
			 (LIST ANCHOR_ST (NTH 4 (NTH 0 LIST2)))
		   )
	    )
	    (SETQ MAIN_LIST (LIST_ADJUSTMENT ELE_LINK_ACA1 LEN))
	  )
	)
	(IF (FILTER_LIST '("FA") LIST2 4)
	  (PROGN
	    (SETQ ELE_LINK_FA1
		   (LIST (LIST S.NO (NTH 1 (NTH 0 LIST2)))
			 (LIST LOC_NO_ST (NTH 2 (NTH 0 LIST2)))
			 (LIST CHAINAGE_ST (NTH 3 (NTH 0 LIST2)))
			 (LIST ANCHOR_ST (NTH 4 (NTH 0 LIST2)))
		   )
	    )
	    (SETQ MAIN_LIST (LIST_ADJUSTMENT ELE_LINK_FA1 LEN))
	  )
	)
	(IF (FILTER_LIST '("AEWA") LIST2 4)
	  (PROGN
	    (SETQ ELE_LINK_AEWA1
		   (LIST (LIST S.NO (NTH 1 (NTH 0 LIST2)))
			 (LIST LOC_NO_ST (NTH 2 (NTH 0 LIST2)))
			 (LIST CHAINAGE_ST (NTH 3 (NTH 0 LIST2)))
			 (LIST ANCHOR_ST (NTH 4 (NTH 0 LIST2)))
		   )
	    )
	    (SETQ MAIN_LIST (LIST_ADJUSTMENT ELE_LINK_AEWA1 LEN))
	  )
	)
      )
    )
    MAIN_LIST
;;;;;;;;;;;;;;;;;;MAIN PROGRAM IN DATA ADJUSTMENT ENDS;;;;;;;;;;;;;;;;;;;;;;;;;;;;;;;;;;;;;;
  )
;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;PRIMARY PRINTING LIST FORMATION FUNCTION;;;;;;;;;;;;;;;;;;;;;;;;;;
  (DEFUN ANCHOR_DATA_LIST (LIST1     TENSION_MUL	 /
			   RESULT    J	       I	 COUNT
			   RESULT_LIST	       LEN
			  )
;;;;;;;;;;;;;;;;;;;;;;;;;;;;;;;;;;;;;;;;;;;;;;;;;;;;;;;;;;;;;;
    (DEFUN ST_END_ADJUSTMENT (LIST1 /)
      (IF (= 2 (LENGTH LIST1))
	(IF (/= (LAST (CAR LIST1)) "START")
	  (REVERSE LIST1)
	  LIST1
	)
	(IF (= (LAST (CAR LIST1)) "END")
	  NIL
	  T
	)
      )
    )
;;;;;;;;;;;;;;;;;;;;;;;;;;;;;;;;;;;;;;;;;;;;;;;;;;;;;;;;;;;;;;;
    (DEFUN MAX_WIRE (LIST1 /)
      (LAST
	(VL-SORT (MAPCAR '(LAMBDA (X) (ATOI (CAR X))) LIST1) '<)
      )
;;;;;;CHECKING FOR REPEATION OF WIRE NUMBER IS PENDING IN THIS
    )
;;;;;;;;;;;;;;;;;;;;;;;;;;MAIN_PROGRAM OF ANCHOR_DATA_LIST;;;;;;;;;;;;;;;;;;;;;;;;
    (SETQ RESULT_LIST NIL)
    (SETQ RESULT LIST1)
    (SETQ J 0)
    (SETQ LEN (FILTER_LIST (LIST " ") RESULT 0))
    (WHILE (< J (LENGTH LEN))
      (SETQ RESULT (VL-REMOVE (NTH J LEN) RESULT))
      (SETQ J (+ J 1))
    )
;;;;;;;;;;
;;;;;;;;;;;;;;;;;;;;;;;;;;;;;;;;;;;;;;;;;;;;;;;;;;;;;;
    (SETQ COUNT (MAX_WIRE RESULT))
    (SETQ I 1)
    (WHILE (AND (<= I COUNT) (/= RESULT NIL))
      (SETQ LEN (FILTER_LIST (LIST (ITOA I)) RESULT 0))
;;;;;;;;;;;;;;;;;;;;;;;;;;;;;;;
      (IF (= (LENGTH LEN) 1)
	(PROGN
	  (SETQ RESULT (VL-REMOVE (CAR LEN) RESULT))
	  (IF (= T (ST_END_ADJUSTMENT LEN))
	    (SETQ RESULT_LIST
		   (CONS (DATA_ADJUSTMENT LEN TENSION_MUL)
			 RESULT_LIST
		   )
	    )
	  )
	)
      )
;;;;;;;;;;;;;;;;;;;;;;;;;;;;;;;
      (IF (= (LENGTH LEN) 2)
	(PROGN (SETQ RESULT (VL-REMOVE (CAR LEN) RESULT))
	       (SETQ RESULT (VL-REMOVE (CADR LEN) RESULT))
	       (SETQ RESULT_LIST
		      (CONS (DATA_ADJUSTMENT (ST_END_ADJUSTMENT LEN) TENSION_MUL)
			    RESULT_LIST
		      )
	       )
	)
      )
      (SETQ I (+ I 1))
;;;;;;;;;;;;;;;;;;;;;;;;;;;;;;
    )
;;;;;;;;;;;;;;;;;;;;;;;;;;;;;;;;;;;;;;;;;;;;;;;;;;;;;;;;;;;;;;
    RESULT_LIST
  )
;;;;;;;;;;;;;;;;;;;;;;;;;;;;;;;;;;;;;;;;;;;;;;;;;;;;;;;;;;;;;;;;;;;;;;;;;;;;;;;;;;;;;;;;;;;;;;;;;;;;;;;;;;;;;;;;;;;;;
;;;;;;;;;;;;;;;;;;;;;;;;;;;;;;;;;;;;;SUB_FUNCTIONS MODULE END;;;;;;;;;;;;;;;;;;;;;;;;;;;;;;;;;;;;;;;;;;;;;;;;;;;;;;;;
;;;;;;;;;;MAIN PROGRAM START
;;;;;;;;;;MAIN PROGRAM START
;;;;;;;;;;;;;;;;;;;;;;;;;;;;;;;;;;;;;;;;;;;;;;;;;;;;;;;;;;;;;;;;;;;;;;;;;;;;;;;;;;;;;;;;;;;;;;;;;;;;;;;;;;;;;;;;;;;;;
  (SETQ EMPTY1 "A4")
  (SETQ EMPTY2 "A6")
  (SETQ EMPTY3 "A8")
  (SETQ EMPTY4 "A10")
;;;;;;;AEWA EMPTY BOX
  (SETQ ROW_WIDTH 6)
;;;;;;;;ROW WIDTH OF TABLE
;;;;;;DATA HANDLING PROGRAM THIS FOR THE RE-ORGANISING OF DATA AND MAPPING OF ANCHORS
  (SETQ LIST1 (ANCHOR_STRUCTURE_MAPPING))
  (SETQ TBL (CAR (ENTSEL)))
  (SETQ TENSION_MUL (GETINT "\n ENTER TENSION_LENGTH MULTIPLE [1/2]:"))
  (SETQ I 0)
  (SETQ MAIN_LIST NIL)
  (WHILE (< I (LENGTH LIST1))
    (SETQ MAIN_LIST
	   (APPEND
	     (MAST_ANC_TAG (CAR (NTH I LIST1)) (CADR (NTH I LIST1)))
	     MAIN_LIST
	   )
    )
    (SETQ I (+ I 1))
  )
  (SETQ MAIN_LIST1 (FILTER_LIST '("BWA" "FTA") MAIN_LIST 4))
  (SETQ MAIN_LIST2 (FILTER_LIST '("ACA") MAIN_LIST 4))
  (SETQ MAIN_LIST3 (FILTER_LIST '("FA") MAIN_LIST 4))
  (SETQ MAIN_LIST4 (FILTER_LIST '("AEWA") MAIN_LIST 4))
  (SETQ TEMP_MAIN_LIST1 (ANCHOR_DATA_LIST MAIN_LIST1 TENSION_MUL))
  (SETQ TEMP_MAIN_LIST2 (ANCHOR_DATA_LIST MAIN_LIST2 TENSION_MUL))
  (SETQ TEMP_MAIN_LIST3 (ANCHOR_DATA_LIST MAIN_LIST3 TENSION_MUL))
  (SETQ TEMP_MAIN_LIST4 (ANCHOR_DATA_LIST MAIN_LIST4 TENSION_MUL))
  (IF (/= MAIN_LIST1 NIL)
    (TBL_PRINT TBL
	       (STRING_SORT TEMP_MAIN_LIST1 0)
	       (CAR (ROW_COL EMPTY1))
	       ROW_WIDTH
    )
  )
  (IF (/= MAIN_LIST2 NIL)
    (TBL_PRINT TBL
	       (STRING_SORT TEMP_MAIN_LIST2 0)
	       (+ (LENGTH TEMP_MAIN_LIST1)
		  (CAR (ROW_COL EMPTY2))
	       )
	       ROW_WIDTH
    )
  )
  (IF (/= MAIN_LIST3 NIL)
    (TBL_PRINT TBL
	       (STRING_SORT TEMP_MAIN_LIST3 0)
	       (+ (LENGTH TEMP_MAIN_LIST2)
		  (LENGTH TEMP_MAIN_LIST1)
		  (CAR (ROW_COL EMPTY3))
	       )
	       ROW_WIDTH
    )
  )
  (IF (/= MAIN_LIST4 NIL)
    (TBL_PRINT TBL
	       (STRING_SORT TEMP_MAIN_LIST4 0)
	       (+ (LENGTH TEMP_MAIN_LIST1)
		  (LENGTH TEMP_MAIN_LIST2)
		  (LENGTH TEMP_MAIN_LIST3)
		  (CAR (ROW_COL EMPTY4))
	       )
	       ROW_WIDTH
    )
  )
;;;;;;;;;;;;;;;;;;;;;;;;;;;;;;;;;;;MAIN PROGRAM END;;;;;;;;;;;;;;;;;;;;;;;;;;;;;;;;;;;;;;;;;;;;;;;;;;;;
)








;;;;;;;;;;;;;;;;;;;;;;;;;;;;;;;;;;;;;;;;;;;;;;;;;;;;;;;;;;;;;;;;;;;;;;;;;;;;;;;;;;;;;;;;;;;;;;;;;;;;;;;;





;;;BACK UP LINK STATEMENTS 
					;(SETQ ELE_LINK_BWA1 (LIST (S.NO (NTH 1 (NTH 1 LIST2))) (LOC_NO_ST (NTH 1 (NTH 2 LIST2))) (CHAINAGE_ST (NTH 1 (NTH 2 LIST2))) (ANCHOR_ST (NTH 1 (NTH 4 LIST2))))) 
					;(SETQ ELE_LINK_ACA1 (LIST (S.NO (NTH 1 (NTH 1 LIST2))) (LOC_NO_ST (NTH 1 (NTH 2 LIST2))) (CHAINAGE_ST (NTH 1 (NTH 2 LIST2))) (ANCHOR_ST (NTH 1 (NTH 4 LIST2)))))
					;(SETQ ELE_LINK_BWA2 (LIST (S.NO (NTH 1 (NTH 1 LIST2))) (LOC_NO_ST (NTH 1 (NTH 2 LIST2))) (CHAINAGE_ST (NTH 1 (NTH 2 LIST2))) (ANCHOR_ST (NTH 1 (NTH 4 LIST2)))
					;    (LOC_NO_END (NTH 2 (NTH 2 LIST2))) (CHAINAGE_END (NTH 2 (NTH 3 LIST2))) (ANCHOR_END (NTH 2 (NTH 4 LIST2))) (CAT_WIRE (TENSION_EVAL LIST2)) (CON_WIRE (TENSION_EVAL LIST2)))) 
					;(SETQ ELE_LINK_ACA2 (LIST (S.NO (NTH 1 (NTH 1 LIST2))) (LOC_NO_ST (NTH 1 (NTH 2 LIST2))) (CHAINAGE_ST (NTH 1 (NTH 2 LIST2))) (ANCHOR_ST (NTH 1 (NTH 4 LIST2)))
					;    (LOC_NO_END (NTH 2 (NTH 2 LIST2))) (CHAINAGE_END (NTH 2 (NTH 3 LIST2))) (ANCHOR_END (NTH 2 (NTH 4 LIST2))) (AC_WIRE (TENSION_EVAL LIST2))))

					;(DEFUN TABLE_FUN (/)
					;  (SETQ S.NO "A3")
					;  (SETQ LOC_NO_ST "B3")
					;  (SETQ CHAINAGE_ST "C3")
					;  (SETQ ANCHOR_ST "D3")
					;  (SETQ LOC_NO_END "E3")
					;  (SETQ CHAINAGE_END "F3")
					;  (SETQ ANCHOR_END "G3")
					; (SETQ CAT_WIRE "H3")
					;  (SETQ CON_WIRE "I3")
					; (SETQ AC_WIRE "J3")
					; (SETQ LS_WIRE "K3")
					;  (SETQ FEEDER_WIRE "L3")
					;  (SETQ EMPTY1 "A4")
					;  (SETQ EMPTY2 "A6")
					; (SETQ EMPTY3 "A8")
					;  (SETQ EMPTY4 "A10");;;;;;;AEWA EMPTY BOX
					; (SETQ ROW_WIDTH 9);;;;;;;;ROW WIDTH OF TABLE
					;)
					;((<Entity name: 7f6837aca60> <Entity name: 7f6835404e0>) (<Entity name: 7f6835670f0> <Entity name: 7f683540980>) (<Entity name: 7f6835dbdf0> <Entity name: 7f68353a540>) (<Entity name: 7f6835f7440> <Entity name: 7f68353a720>) (<Entity name: 7f68355b140> <Entity name: 7f683548180>) (<Entity name: 7f68355ba00> <Entity name: 7f683548540>) (<Entity name: 7f68379fdc0> <Entity name: 7f683540b60>))
