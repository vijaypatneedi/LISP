(DEFUN C:UPDATE_TOTAL_SPANS_GPS ( / BLOCKS_LIST MAST_TTC_DIR MAST_LIST_DNLINE MAST_LIST_UPLINE)
  
  (SETQ TRACK_ENTITY_UPTRACK (CAR(ENTSEL "\nSELECT TRACK ALIGNMENT FOR UP TRACK (DN LINE):")))
  (SETQ STARTING_MAST (CAR(ENTSEL "\nSELECT STARTING_MAST:")))
  (SETQ STARTING_POINT (GETPOINT "\nENTER STARTING POINT FOR UP TRACK (DN LINE):"))
       
  (SETQ BLOCKS_LIST (FORM_SSSET (SSGET "X" (LIST (CONS 0 "INSERT")))))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_LIST_DNLINE (SINGLE_ELE_LIST (FILTER_LIST '("DN") MAST_TTC_DIR 1) 0))
  (SETQ MAST_LIST_UPLINE (SINGLE_ELE_LIST (FILTER_LIST '("UP") MAST_TTC_DIR 1) 0))
  (SETQ MAST_LIST_DNLINE (SORT_FUN (ENTITY_DFX MAST_LIST_DNLINE 10 -1) 1 0))
  (SETQ MAST_LIST_UPLINE (SORT_FUN (ENTITY_DFX MAST_LIST_UPLINE 10 -1) 1 0))
  
  (SETQ MAST_LIST_DNLINE (COMBINE_LIST_ELEMENTS (GET_PROJECTION_FROM_POINT_LIST_FINAL TRACK_ENTITY_UPTRACK (BUILD_LIST MAST_LIST_DNLINE (LIST 0 1)) 1)))
  (SETQ MAST_LIST_UPLINE (COMBINE_LIST_ELEMENTS (GET_PROJECTION_FROM_POINT_LIST_FINAL TRACK_ENTITY_UPTRACK (BUILD_LIST MAST_LIST_UPLINE (LIST 0 1)) 1)))
  
  (SETQ MAST_LIST_DNLINE (SORT_ENTITIES_ALONG_CURVE TRACK_ENTITY_UPTRACK MAST_LIST_DNLINE (LIST 1 STARTING_POINT) 2 1))
  (SETQ MAST_LIST_UPLINE (SORT_ENTITIES_ALONG_CURVE TRACK_ENTITY_UPTRACK MAST_LIST_UPLINE (LIST 1 STARTING_POINT) 2 1))
  (UPDATE_TOTAL_SPANS_GPS1 STARTING_MAST TRACK_ENTITY_UPTRACK (SINGLE_ELE_LIST MAST_LIST_DNLINE 0))
  (UPDATE_TOTAL_SPANS_GPS1 STARTING_MAST TRACK_ENTITY_UPTRACK (SINGLE_ELE_LIST MAST_LIST_UPLINE 0))
  
)

(DEFUN UPDATE_TOTAL_SPANS_GPS1 ( STARTING_MAST TRACK_CENTER MAST_LIST  / SSSET STARTING_MAST TRACK_CENTER ENT_LIST PROJECTTION_POINTS )

   (COMMAND "UCS" "W")
   (SETQ ENT_LIST SSSET)
   (SETQ ENT_LIST (EXTRACT_ENTITY_INFO ENT_LIST 1 3))
   (SETQ ENT_LIST (SORT_MASTS ENT_LIST STARTING_MAST))
   (SETQ PROJECTTION_POINTS (SINGLE_ELE_LIST (GET_PROJECTION_FROM_POINT_LIST_FINAL TRACK_CENTER ENT_LIST 1) 1))
   (UPDATE_SPAN_GPS  TRACK_CENTER  (SINGLE_ELE_LIST ENT_LIST 0) PROJECTTION_POINTS)
   (COMMAND "UCS" "P")
  
)



(DEFUN UPDATE_TOTAL_CHAINAGES_SPLIT_GPS (KM_LIST UPLIST DNLIST POLYLINE_ENTITY / I TEMP_ELE1 TEMP_ELE2 TEMP_ELE3 F LOC_NO ST_CH ENT_LIST TEMP_KM ST_CH_UP ST_CH_DN)
     (SETQ F 0 TEMP_ELE1 NIL TEMP_ELE2 NIL TEMP_ELE3 NIL TEMP_KM NIL)
   (setq dcl_id (load_dialog "DISPLAY_INFO.dcl"))
   (new_dialog "DISPLAY_INFO" dcl_id)
  (WHILE (< F (LENGTH KM_LIST))
    (SETQ TEMP_ELE1 (NTH F KM_LIST) TEMP_ELE2 (NTH F UPLIST) TEMP_ELE3 (NTH F DNLIST) TEMP_ELE4 (NTH (+ F 1) KM_LIST))
     (SET_TILE "INFO" (STRCAT "UPDATING KM " (ITOA (+ F 1)) " OF "  (ITOA (LENGTH KM_LIST))))
     (SET_TILE "PERCENTAGE" (STRCAT (RTOS (/ (* (+ F 1) 100) (ATOF (RTOS (LENGTH KM_LIST) 2 2)) ) 2 2) "%" "COMPLETED"))
    (IF (= F (- (LENGTH KM_LIST) 1))
      (PROGN
      (SET_TILE "INFO" (STRCAT "ALL " "KILOMETER" " LOCATIONS ARE UPDATED SUCESSFULLY"))
      (SET_TILE "PERCENTAGE" "PRESS OK TO CONTINUE")
      )
    )
    
    (SETQ ATTR_LIST (GET_ATTRIBUTES (NTH 0 TEMP_ELE1)))
    (SETQ TEMP_KM (NTH 1 (ASSOC "KM" ATTR_LIST)))
    (SETQ TEMP_KM (SUBSTR TEMP_KM (+ (VL-STRING-POSITION (ASCII ":") TEMP_KM) 2)))

    (IF (/= TEMP_ELE4 NIL)
    (PROGN
    (SETQ ATTR_LIST1 (GET_ATTRIBUTES (NTH 0 TEMP_ELE4)))
    (SETQ TEMP_KM1 (NTH 1 (ASSOC "KM" ATTR_LIST1)))
    (SETQ TEMP_KM1 (SUBSTR TEMP_KM1 (+ (VL-STRING-POSITION (ASCII ":") TEMP_KM1) 2)))
    )
    )
    
    ;(SETQ TEMP_ELE2 (SORT_MASTS_NEW TEMP_ELE2 TEMP_ELE1 1 2))
    ;(SETQ TEMP_ELE3 (SORT_MASTS_NEW TEMP_ELE3 TEMP_ELE1 1 2))
    ;(SETQ LOC_NO (STRCAT (NTH 0 TEMP_ELE1) "/" STARTING_LOCATION))
    ;(VLAX-CURVE-GETCLOSESTPOINTTO POLYLINE_ENTITY (NTH 1 (NTH 0 TEMP_ELE3)) T)
    (IF (= F 0)
    (PROGN
    (SETQ ST_CH_UP (STRCAT TEMP_KM "/" (RTOS (DISTANCE_ON_CURVE_GPS  POLYLINE_ENTITY (NTH 2 TEMP_ELE1) (NTH 1 (NTH 0 TEMP_ELE2))) 2 2)))
    (SETQ ST_CH_DN (STRCAT TEMP_KM "/" (RTOS (DISTANCE_ON_CURVE_GPS  POLYLINE_ENTITY (NTH 2 TEMP_ELE1) (NTH 1 (NTH 0 TEMP_ELE3))) 2 2)))
    )
    )
    
    (SETQ TEMP_ELE2 (UPDATE_CHAINAGES_SPLIT_GPS ST_CH_UP TEMP_ELE2 "DN"))
    (SETQ TEMP_ELE3 (UPDATE_CHAINAGES_SPLIT_GPS ST_CH_DN TEMP_ELE3 "UP"))
    (SETQ END_CH_UP (NTH 0 (NTH 1 (NTH (- (LENGTH TEMP_ELE2) 1) TEMP_ELE2))) END_SPAN_UP (NTH 2 (NTH 1 (NTH (- (LENGTH TEMP_ELE2) 1) TEMP_ELE2))))
    (SETQ END_CH_DN (NTH 0 (NTH 1 (NTH (- (LENGTH TEMP_ELE3) 1) TEMP_ELE3))) END_SPAN_DN (NTH 2 (NTH 1 (NTH (- (LENGTH TEMP_ELE3) 1) TEMP_ELE3))))
    (SETQ ST_CH_UP  (- END_SPAN_UP (- 1000 END_CH_UP)))
    (SETQ ST_CH_DN  (- END_SPAN_DN (- 1000 END_CH_DN)))
    (IF (/= TEMP_ELE4 NIL)
    (PROGN
    (SETQ ST_CH_UP (STRCAT TEMP_KM1 "/" (RTOS ST_CH_UP 2 2)))
    (SETQ ST_CH_DN (STRCAT TEMP_KM1 "/" (RTOS ST_CH_DN 2 2)))
    )
    )
    (SETQ TEMP_MAIN_LIST (ASSIGN_LOCATION_NUMBERS (SORT_MULTILEVEL (APPEND (ADD_LISTS TEMP_ELE2 (N_ELE_LIST "DN" (LENGTH TEMP_ELE2))) (ADD_LISTS TEMP_ELE3 (N_ELE_LIST "UP" (LENGTH TEMP_ELE3)))) 1 0 1)))
    (UPDATE_LOC_NUMBERS_GPS TEMP_MAIN_LIST TEMP_KM)
    (SETQ F (+ F 1))
  )
  (setq ddiag(start_dialog))
)


(DEFUN C:UPDATE_TOTAL_CHAINAGES_GPS ( / )

  (SETQ WPT1 (GETPOINT "\nSELECT POINT1:"))
  (SETQ WPT2 (GETPOINT "\nSELECT POINT2:"))
  (SETQ BLOCKS_LIST (FORM_SSSET (SSGET "W" WPT1 WPT2 (LIST (CONS 0 "INSERT")))))
  (SETQ TRACK_ENTITY_UPTRACK (ENTSEL "\nSELECT TRACK ALIGNMENT FOR UP TRACK (DN LINE):"))
  (SETQ STARTING_POINT (GETPOINT "\nPICK STARTING POINT"))
  (SETQ BLOCK_NAME_LIST (EXTRACT_ENTITY_INFO2 BLOCKS_LIST))
  (SETQ KM_STONE_LIST (FILTER_LIST (LIST "KM_NEW" "KM_STONE" "KMNEW" "KMSTONE") BLOCK_NAME_LIST 1))
  (SETQ KM_STONE_LIST (SORT_FUN (ENTITY_DFX (SINGLE_ELE_LIST KM_STONE_LIST 0) 10 -1) 1 0))
  (SETQ KM_STONE_COORDINATES (COMBINE_LIST_ELEMENTS (GET_PROJECTION_FROM_POINT_LIST_FINAL (NTH 0 TRACK_ENTITY_UPTRACK) (BUILD_LIST KM_STONE_LIST (LIST 0 1)) 1)))
  (SETQ KM_STONE_COORDINATES (SORT_ENTITIES_ALONG_CURVE (NTH 0 TRACK_ENTITY_UPTRACK) KM_STONE_COORDINATES (LIST 1 STARTING_POINT) 2 1))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_UP (FILTER_LIST '("UP") MAST_TTC_DIR 1))
  (SETQ MAST_DN (FILTER_LIST '("DN") MAST_TTC_DIR 1))

  (SETQ MAST_UP (ATTRIBUTES_FROM_ENTITIES (SINGLE_ELE_LIST MAST_UP 0) "SPAN1" 0))
  (SETQ MAST_DN (ATTRIBUTES_FROM_ENTITIES (SINGLE_ELE_LIST MAST_DN 0) "SPAN1" 0))

  (SETQ DNLINE_MASTS (BUILD_LIST (ADD_LISTS MAST_UP (ENTITY_DFX (SINGLE_ELE_LIST MAST_UP 0) 10 -1)) (LIST 0 3 1)))
  (SETQ UPLINE_MASTS (BUILD_LIST (ADD_LISTS MAST_DN (ENTITY_DFX (SINGLE_ELE_LIST MAST_DN 0) 10 -1)) (LIST 0 3 1)))
 
  (SETQ UPLINE_MAST_ENTITIES (BUILD_LIST (COMBINE_LIST_ELEMENTS (GET_PROJECTION_FROM_POINT_LIST_FINAL (NTH 0 TRACK_ENTITY_UPTRACK) (ADD_LISTS UPLINE_MASTS (N_ELE_LIST "DN" (LENGTH UPLINE_MASTS))) 1)) (LIST 0 4 2 3)))
  (SETQ DNLINE_MAST_ENTITIES (BUILD_LIST (COMBINE_LIST_ELEMENTS (GET_PROJECTION_FROM_POINT_LIST_FINAL (NTH 0 TRACK_ENTITY_UPTRACK) (ADD_LISTS DNLINE_MASTS (N_ELE_LIST "UP" (LENGTH DNLINE_MASTS))) 1)) (LIST 0 4 2 3)))
  
  (SETQ UPLINE_MASTS (FIND_IN_BETWEEN_GPS KM_STONE_COORDINATES UPLINE_MAST_ENTITIES (NTH 0 TRACK_ENTITY_UPTRACK) 2 1 (NTH 0 KM_STONE_COORDINATES)))
  (SETQ DNLINE_MASTS (FIND_IN_BETWEEN_GPS KM_STONE_COORDINATES DNLINE_MAST_ENTITIES (NTH 0 TRACK_ENTITY_UPTRACK) 2 1 (NTH 0 KM_STONE_COORDINATES)))
  (UPDATE_TOTAL_CHAINAGES_SPLIT_GPS  (VL-REMOVE (NTH (- (LENGTH KM_STONE_COORDINATES) 1) KM_STONE_COORDINATES) KM_STONE_COORDINATES) (SINGLE_ELE_LIST (SORT_ENTITIES_ALONG_CURVE1 (NTH 0 TRACK_ENTITY_UPTRACK) UPLINE_MASTS (NTH 0 KM_STONE_COORDINATES) 1 2) 0) (SINGLE_ELE_LIST (SORT_ENTITIES_ALONG_CURVE1 (NTH 0 TRACK_ENTITY_UPTRACK) DNLINE_MASTS (NTH 0 KM_STONE_COORDINATES) 1 2) 0) (NTH 0 TRACK_ENTITY_UPTRACK))


)



(DEFUN C:UPDATE_TOTAL_CHAINAGES_GPS2 ( / )

  (SETQ WPT1 (GETPOINT "\nSELECT POINT1:"))
  (SETQ WPT2 (GETPOINT "\nSELECT POINT2:"))
  (SETQ ST_CH_DN (GETSTRING "\nENTER STARTING CHAINAGE OF DNLINE"))
  (SETQ ST_CH_UP (GETSTRING "\nENTER STARTING CHAINAGE OF UPLINE"))
  (SETQ BLOCKS_LIST (FORM_SSSET (SSGET "W" WPT1 WPT2 (LIST (CONS 0 "INSERT")))))
  (SETQ TRACK_ENTITY_UPTRACK (ENTSEL "\nSELECT TRACK ALIGNMENT FOR UP TRACK (DN LINE):"))
  (SETQ STARTING_POINT (GETPOINT "\nPICK STARTING POINT"))
  (SETQ BLOCK_NAME_LIST (EXTRACT_ENTITY_INFO2 BLOCKS_LIST))
  (SETQ KM_STONE_LIST (FILTER_LIST (LIST "KM_NEW" "KM_STONE" "KMNEW" "KMSTONE") BLOCK_NAME_LIST 1))
  (SETQ KM_STONE_LIST (SORT_FUN (ENTITY_DFX (SINGLE_ELE_LIST KM_STONE_LIST 0) 10 -1) 1 0))
  (SETQ KM_STONE_COORDINATES (COMBINE_LIST_ELEMENTS (GET_PROJECTION_FROM_POINT_LIST_FINAL (NTH 0 TRACK_ENTITY_UPTRACK) (BUILD_LIST KM_STONE_LIST (LIST 0 1)) 1)))
  (SETQ KM_STONE_COORDINATES (SORT_ENTITIES_ALONG_CURVE (NTH 0 TRACK_ENTITY_UPTRACK) KM_STONE_COORDINATES (LIST 1 STARTING_POINT) 2 1))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_UP (FILTER_LIST '("UP") MAST_TTC_DIR 1))
  (SETQ MAST_DN (FILTER_LIST '("DN") MAST_TTC_DIR 1))
  (SETQ MAST_UP (ATTRIBUTES_FROM_ENTITIES (SINGLE_ELE_LIST MAST_UP 0) "SPAN1" 0))
  (SETQ MAST_DN (ATTRIBUTES_FROM_ENTITIES (SINGLE_ELE_LIST MAST_DN 0) "SPAN1" 0))

  (SETQ DNLINE_MASTS (BUILD_LIST (ADD_LISTS MAST_UP (ENTITY_DFX (SINGLE_ELE_LIST MAST_UP 0) 10 -1)) (LIST 0 3 1)))
  (SETQ UPLINE_MASTS (BUILD_LIST (ADD_LISTS MAST_DN (ENTITY_DFX (SINGLE_ELE_LIST MAST_DN 0) 10 -1)) (LIST 0 3 1)))
 
  (SETQ UPLINE_MAST_ENTITIES (BUILD_LIST (COMBINE_LIST_ELEMENTS (GET_PROJECTION_FROM_POINT_LIST_FINAL (NTH 0 TRACK_ENTITY_UPTRACK) (ADD_LISTS UPLINE_MASTS (N_ELE_LIST "DN" (LENGTH UPLINE_MASTS))) 1)) (LIST 0 4 2 3)))
  (SETQ DNLINE_MAST_ENTITIES (BUILD_LIST (COMBINE_LIST_ELEMENTS (GET_PROJECTION_FROM_POINT_LIST_FINAL (NTH 0 TRACK_ENTITY_UPTRACK) (ADD_LISTS DNLINE_MASTS (N_ELE_LIST "UP" (LENGTH DNLINE_MASTS))) 1)) (LIST 0 4 2 3)))
  
  (SETQ UPLINE_MASTS (FIND_IN_BETWEEN_GPS KM_STONE_COORDINATES UPLINE_MAST_ENTITIES (NTH 0 TRACK_ENTITY_UPTRACK) 2 1 (NTH 0 KM_STONE_COORDINATES)))
  (SETQ DNLINE_MASTS (FIND_IN_BETWEEN_GPS KM_STONE_COORDINATES DNLINE_MAST_ENTITIES (NTH 0 TRACK_ENTITY_UPTRACK) 2 1 (NTH 0 KM_STONE_COORDINATES)))
  (UPDATE_TOTAL_CHAINAGES_SPLIT_GPS2  (VL-REMOVE (NTH (- (LENGTH KM_STONE_COORDINATES) 1) KM_STONE_COORDINATES) KM_STONE_COORDINATES) (SINGLE_ELE_LIST (SORT_ENTITIES_ALONG_CURVE1 (NTH 0 TRACK_ENTITY_UPTRACK) UPLINE_MASTS (NTH 0 KM_STONE_COORDINATES) 1 2) 0) (SINGLE_ELE_LIST (SORT_ENTITIES_ALONG_CURVE1 (NTH 0 TRACK_ENTITY_UPTRACK) DNLINE_MASTS (NTH 0 KM_STONE_COORDINATES) 1 2) 0) (NTH 0 TRACK_ENTITY_UPTRACK) ST_CH_DN ST_CH_UP )


)



(DEFUN UPDATE_TOTAL_CHAINAGES_SPLIT_GPS2 (KM_LIST UPLIST DNLIST POLYLINE_ENTITY ST_CH_DN1 ST_CH_UP1 / I TEMP_KM TEMP_KM1 TEMP_ELE1 TEMP_ELE2 TEMP_ELE3 F LOC_NO ST_CH ENT_LIST TEMP_KM ST_CH_UP ST_CH_DN)
     (SETQ F 0 TEMP_ELE1 NIL TEMP_ELE2 NIL TEMP_ELE3 NIL TEMP_KM NIL)
   (setq dcl_id (load_dialog "DISPLAY_INFO.dcl"))
   (new_dialog "DISPLAY_INFO" dcl_id)
  (WHILE (< F (LENGTH KM_LIST))
    (SETQ TEMP_ELE1 (NTH F KM_LIST) TEMP_ELE2 (NTH F UPLIST) TEMP_ELE3 (NTH F DNLIST) TEMP_ELE4 (NTH (+ F 1) KM_LIST))
    (SET_TILE "INFO" (STRCAT "UPDATING KM " (ITOA (+ F 1)) " OF "  (ITOA (LENGTH KM_LIST))))
     (SET_TILE "PERCENTAGE" (STRCAT (RTOS (/ (* (+ F 1) 100) (ATOF (RTOS (LENGTH KM_LIST) 2 2)) ) 2 2) "%" "COMPLETED"))
    (IF (= F (- (LENGTH KM_LIST) 1))
      (PROGN
      (SET_TILE "INFO" (STRCAT "ALL " "KILOMETER" " LOCATIONS ARE UPDATED SUCESSFULLY"))
      (SET_TILE "PERCENTAGE" "PRESS OK TO CONTINUE")
      )
    )
    
    (SETQ ATTR_LIST (GET_ATTRIBUTES (NTH 0 TEMP_ELE1)))
    (SETQ TEMP_KM (NTH 1 (ASSOC "KM" ATTR_LIST)))
    (SETQ TEMP_KM (SUBSTR TEMP_KM (+ (VL-STRING-POSITION (ASCII ":") TEMP_KM) 2)))

    (IF (/= TEMP_ELE4 NIL)
    (PROGN
    (SETQ ATTR_LIST1 (GET_ATTRIBUTES (NTH 0 TEMP_ELE4)))
    (SETQ TEMP_KM1 (NTH 1 (ASSOC "KM" ATTR_LIST1)))
    (SETQ TEMP_KM1 (SUBSTR TEMP_KM1 (+ (VL-STRING-POSITION (ASCII ":") TEMP_KM1) 2)))
    )
    )
    
    ;(SETQ TEMP_ELE2 (SORT_MASTS_NEW TEMP_ELE2 TEMP_ELE1 1 2))
    ;(SETQ TEMP_ELE3 (SORT_MASTS_NEW TEMP_ELE3 TEMP_ELE1 1 2))
    ;(SETQ LOC_NO (STRCAT (NTH 0 TEMP_ELE1) "/" STARTING_LOCATION))
    ;(VLAX-CURVE-GETCLOSESTPOINTTO POLYLINE_ENTITY (NTH 1 (NTH 0 TEMP_ELE3)) T)
    (IF (= F 0)
    (PROGN
    (SETQ ST_CH_UP (STRCAT TEMP_KM "/"  ST_CH_DN1))
    (SETQ ST_CH_DN (STRCAT TEMP_KM "/" ST_CH_UP1))
    )
    )
    
    (SETQ TEMP_ELE2 (UPDATE_CHAINAGES_SPLIT_GPS ST_CH_UP TEMP_ELE2 "DN"))
    (SETQ TEMP_ELE3 (UPDATE_CHAINAGES_SPLIT_GPS ST_CH_DN TEMP_ELE3 "UP"))
    (SETQ END_CH_UP (NTH 0 (NTH 1 (NTH (- (LENGTH TEMP_ELE2) 1) TEMP_ELE2))) END_SPAN_UP (NTH 2 (NTH 1 (NTH (- (LENGTH TEMP_ELE2) 1) TEMP_ELE2))))
    (SETQ END_CH_DN (NTH 0 (NTH 1 (NTH (- (LENGTH TEMP_ELE3) 1) TEMP_ELE3))) END_SPAN_DN (NTH 2 (NTH 1 (NTH (- (LENGTH TEMP_ELE3) 1) TEMP_ELE3))))
    (SETQ ST_CH_UP  (- END_SPAN_UP (- 1000 END_CH_UP)))
    (SETQ ST_CH_DN  (- END_SPAN_DN (- 1000 END_CH_DN)))
    (IF (/= TEMP_ELE4 NIL)
    (PROGN
    (SETQ ST_CH_UP (STRCAT TEMP_KM1 "/" (RTOS ST_CH_UP 2 2)))
    (SETQ ST_CH_DN (STRCAT TEMP_KM1 "/" (RTOS ST_CH_DN 2 2)))
    )
    )
    (SETQ TEMP_MAIN_LIST (ASSIGN_LOCATION_NUMBERS (SORT_MULTILEVEL (APPEND (ADD_LISTS TEMP_ELE2 (N_ELE_LIST "DN" (LENGTH TEMP_ELE2))) (ADD_LISTS TEMP_ELE3 (N_ELE_LIST "UP" (LENGTH TEMP_ELE3)))) 1 0 1)))
    (UPDATE_LOC_NUMBERS_GPS TEMP_MAIN_LIST TEMP_KM)
    (SETQ F (+ F 1))
  )
  (setq ddiag(start_dialog))
)
