(DEFUN C:UPDATE_CLEAR_SPAN_GPS(  / SSSET STARTING_MAST TRACK_CENTER ENT_LIST PROJECTTION_POINTS )
   (SETQ WPT1 (GETPOINT "ENTER STARTING POINT IN LOP"))
   (SETQ WPT2 (GETPOINT "\n ENTER ENDING POINT IN LOP"))
   (SETQ PORTAL_ENTITIES (YARD_DATA_COLLECT WPT1 WPT2 '("PORTAL" "SS5") 1 3))
   (COMMAND "UCS" "W")
   (SETQ I 0 CS NIL)
   (WHILE (< I (LENGTH PORTAL_ENTITIES))
     (IF (/= (VL-POSITION (VLAX-GET-PROPERTY (VLAX-ENAME->VLA-OBJECT (NTH 0 (NTH I PORTAL_ENTITIES))) 'EFFECTIVENAME) (LIST "PORTAL" "SS5")) NIL)
             (PROGN
             (SETQ CS (RTOS (NTH 1 (NTH 0 (GET_DYNAMIC_PROPERTIES (NTH 0 (NTH I PORTAL_ENTITIES)) (LIST "STL1")))) 2 2))
             (SETQ CS (STRCAT "CS-" CS))
             (MODIFY_ATTRIBUTES (NTH 0 (NTH I PORTAL_ENTITIES)) (LIST "CS1" "CS2") (LIST CS CS))
	     )
     )
     (SETQ I (+ I 1))
   )
   (COMMAND "UCS" "P")
)



(DEFUN C:UPDATE_FOUNDATION_CENTER_CO-ORDINATES(  / SSSET STARTING_MAST TRACK_CENTER ENT_LIST PROJECTTION_POINTS )
   (SETQ WPT1 (GETPOINT "ENTER STARTING POINT IN LOP"))
   (SETQ WPT2 (GETPOINT "\n ENTER ENDING POINT IN LOP"))
  (SETQ STRUCTURE_ENTITIES (YARD_DATA_COLLECT WPT1 WPT2 '("SINGLE_CANT_MAST" "DOUBLE_CANT_MAST" "TRIPLE_CANT_MAST" "TTC" "SS1" "SS2" "SS3" "SS4" "PORTAL" "SS5") 1 3))
  (SETQ TRACK_ENTITY_DN (CAR(ENTSEL "\nSELECT DN TRACK ALIGNMENT:")))
  (SETQ TRACK_ENTITY_UP (CAR(ENTSEL "\nSELECT UP TRACK ALIGNMENT:")))
   
   
   (COMMAND "UCS" "W")
   (SETQ I 0 CS NIL)
   (WHILE (< I (LENGTH STRUCTURE_ENTITIES))
     (SETQ ROTATION (VLAX-GET-PROPERTY (VLAX-ENAME->VLA-OBJECT (NTH 0 (NTH I STRUCTURE_ENTITIES))) 'ROTATION))
     (IF (/= (VL-POSITION (VLAX-GET-PROPERTY (VLAX-ENAME->VLA-OBJECT (NTH 0 (NTH I STRUCTURE_ENTITIES))) 'EFFECTIVENAME) (LIST "PORTAL" "SS5")) NIL)
             (PROGN
	     (IF (= (SUBSTR (NTH 0 (SINGLE_ELE_LIST (EXTRACT_ATTRIBUTES (NTH 0 (NTH I STRUCTURE_ENTITIES)) (LIST "MAST_TYPE2" ) 1) 1)) 2 1) "N")
             (SETQ TEMP_CO-ORDINATES1 (MAPCAR 'RTOS (POLAR (NTH 1 (NTH I STRUCTURE_ENTITIES)) (+ (* 3 (/ PI 2)) ROTATION) 0.275)))
	     )
	     (IF (/= (VL-POSITION (SUBSTR (NTH 0 (SINGLE_ELE_LIST (EXTRACT_ATTRIBUTES (NTH 0 (NTH I STRUCTURE_ENTITIES)) (LIST "MAST_TYPE2" ) 1) 1)) 2 1) (LIST "O" "R")) NIL)
	     (SETQ TEMP_CO-ORDINATES1 (MAPCAR 'RTOS (POLAR (NTH 1 (NTH I STRUCTURE_ENTITIES)) (+ (* 3 (/ PI 2)) ROTATION) 0.3)))
	     )
	     
	     (IF (= (SUBSTR (NTH 0 (SINGLE_ELE_LIST (EXTRACT_ATTRIBUTES (NTH 0 (NTH I STRUCTURE_ENTITIES)) (LIST "MAST_TYPE1" ) 1) 1)) 2 1) "N")
	     (SETQ TEMP_CO-ORDINATES2 (MAPCAR 'RTOS (POLAR (NTH 1 (NTH I STRUCTURE_ENTITIES)) (+ (* 1 (/ PI 2)) ROTATION) (+ (NTH 1 (NTH 0 (GET_DYNAMIC_PROPERTIES (NTH 0 (NTH I STRUCTURE_ENTITIES)) (LIST "STL1")))) 0.275))))
	     )

	     (IF (/= (VL-POSITION (SUBSTR (NTH 0 (SINGLE_ELE_LIST (EXTRACT_ATTRIBUTES (NTH 0 (NTH I STRUCTURE_ENTITIES)) (LIST "MAST_TYPE2" ) 1) 1)) 2 1) (LIST "O" "R")) NIL)
	     (SETQ TEMP_CO-ORDINATES2 (MAPCAR 'RTOS (POLAR (NTH 1 (NTH I STRUCTURE_ENTITIES)) (+ (* 1 (/ PI 2)) ROTATION) (+ (NTH 1 (NTH 0 (GET_DYNAMIC_PROPERTIES (NTH 0 (NTH I STRUCTURE_ENTITIES)) (LIST "STL1")))) 0.3))))
	     )
	     
             (MODIFY_ATTRIBUTES (NTH 0 (NTH I STRUCTURE_ENTITIES)) (LIST "DUMMY_VARIABLE5" "DUMMY_VARIABLE1" ) (LIST (STRCAT "(" (NTH 0 TEMP_CO-ORDINATES1) " , " (NTH 1 TEMP_CO-ORDINATES1) ")" )  (STRCAT "(" (NTH 0 TEMP_CO-ORDINATES2) " , " (NTH 1 TEMP_CO-ORDINATES2) ")" )))
	     )
     )

     (IF (/= (VL-POSITION (VLAX-GET-PROPERTY (VLAX-ENAME->VLA-OBJECT (NTH 0 (NTH I STRUCTURE_ENTITIES))) 'EFFECTIVENAME) (LIST "SINGLE_CANT_MAST" "DOUBLE_CANT_MAST" "TRIPLE_CANT_MAST" "TTC" "SS1" "SS2" "SS3" "SS4")) NIL)
             (PROGN
             (SETQ FLIP (NTH 1 (NTH 0 (GET_DYNAMIC_PROPERTIES (NTH 0 (NTH I STRUCTURE_ENTITIES)) '("STF1")))))
	     (SETQ TEMP_IMP (NTH 0 (SINGLE_ELE_LIST (EXTRACT_ATTRIBUTES (NTH 0 (NTH I STRUCTURE_ENTITIES)) (LIST "IMPLANTATION1" ) 1) 1)))
	     (IF (= FLIP 0)
             (SETQ TEMP_CO-ORDINATES (MAPCAR 'RTOS (POLAR (VLAX-CURVE-GETCLOSESTPOINTTO TRACK_ENTITY_DN (NTH 1 (NTH I STRUCTURE_ENTITIES)) T) (+ (* 1 (/ PI 2)) ROTATION) (+ (ATOF TEMP_IMP) 0.2))))
             (SETQ TEMP_CO-ORDINATES (MAPCAR 'RTOS (POLAR (VLAX-CURVE-GETCLOSESTPOINTTO TRACK_ENTITY_DN (NTH 1 (NTH I STRUCTURE_ENTITIES)) T) (+ (* 3 (/ PI 2)) ROTATION) (+ (ATOF TEMP_IMP) 0.2))))
             )
             (MODIFY_ATTRIBUTES (NTH 0 (NTH I STRUCTURE_ENTITIES)) (LIST "DUMMY_VARIABLE1" ) (LIST (STRCAT "(" (NTH 0 TEMP_CO-ORDINATES) " , " (NTH 1 TEMP_CO-ORDINATES) ")" )))
	     )
     )

     
     (SETQ I (+ I 1))
   )
   (COMMAND "UCS" "P")
)



(DEFUN C:UPDATE_CHAINAGES_PORTAL_EMP-4 ( / SSSET LOC_NO ST_CH ENT_LIST BS_PT VALUES VALUES1 VALUES2 VALUES3 POINT POINT1 POINT2 POINT3 ENT_LIST_SPAN I LOC CH TEMP_ELE SCALE LOC_NO_DN VALUES_DN VALUES1_DN VALUES2_DN VALUES3_DN POINT_DN POINT1_DN POINT2_DN POINT3_DN LOC_DN CS_REFERENCE_X CS_REFERENCE_Y CS_REFERENCE CS_REFERENCE1 FDN_REFERENCE FDN_REFERENCE1)
  (SETQ WPT1 (GETPOINT "ENTER STARTING POINT IN LOP"))
  (SETQ WPT2 (GETPOINT "\n ENTER ENDING POINT IN LOP"))
  (SETQ STRUCTURE_ENTITIES (YARD_DATA_COLLECT WPT1 WPT2 '("PORTAL" "SS5") 1 3))
  
  
  
  (SETQ ST_CH (GETSTRING "\nENTER STARTING PORTAL CHAINAGE (CONTINUOUS) :"))
  (SETQ ST_CH1 (GETSTRING "\nENTER STARTING PORTAL CHAINAGE (DFCC) :"))
  
  (SETQ TRACK_ENTITY (CAR(ENTSEL "\nSELECT TRACK ALIGNMENT:")))
  (SETQ STARTING_PORTAL (CAR(ENTSEL "\nSELECT STARTING PORTAL:")))
  (SETQ	KM_NO (SUBSTR ST_CH 1 (VL-STRING-POSITION (ASCII "/") ST_CH)))
  (SETQ	ST_CH	(SUBSTR	ST_CH (+ (VL-STRING-POSITION (ASCII "/") ST_CH) 2)))
  
  (SETQ	KM_NO1	(SUBSTR	ST_CH1 1 (VL-STRING-POSITION (ASCII "/") ST_CH1)))
  (SETQ	ST_CH1	(SUBSTR	ST_CH1 (+ (VL-STRING-POSITION (ASCII "/") ST_CH1) 2)))
	
  (SETQ ENT_LIST (GET_PROJECTION_FROM_POINT_LIST_PORTAL TRACK_ENTITY STRUCTURE_ENTITIES 1))
  (SETQ ENT_LIST (BUILD_LIST ENT_LIST (LIST 0 2)))
  (SETQ ENT_LIST (SORT_MASTS ENT_LIST STARTING_PORTAL))
  

  


  (SETQ I 0)
  (WHILE (< I (LENGTH ENT_LIST))
    
    
    (SETQ CH (STRCAT KM_NO "/" ST_CH))
    (SETQ CH1 (STRCAT KM_NO1 "/" ST_CH1))
    
    (SETQ TEMP_ELE  (NTH I ENT_LIST))
    
    
    (MODIFY_ATTRIBUTES (NTH 0 TEMP_ELE) (LIST  "CHAINAGE1" "CHAINAGE3") (LIST  CH CH1))
    (MODIFY_ATTRIBUTES (NTH 0 TEMP_ELE) (LIST  "CHAINAGE2" "CHAINAGE4") (LIST  CH CH1))

    (IF (/= (NTH (+ I 1) ENT_LIST) NIL) (SETQ TEMP_SPAN (APPROXIMATE_SPAN (DISTANCE_ON_CURVE_GPS TRACK_ENTITY (NTH 1 TEMP_ELE) (NTH 1 (NTH (+ I 1) ENT_LIST))) 0.68)))
    
    
    
    
    (IF (<= (+ (ATOF ST_CH) TEMP_SPAN) 1000)
    (PROGN
    (SETQ ST_CH (RTOS (+ (ATOF ST_CH) TEMP_SPAN) 2 2))
    )

    (PROGN
    
    (SETQ ST_CH (RTOS (- (+ (ATOF ST_CH) TEMP_SPAN) 1000 ) 2 2))
    )
      
    )

    (IF (<= (+ (ATOF ST_CH1) TEMP_SPAN) 1000)
    (PROGN
    (SETQ ST_CH1 (RTOS (+ (ATOF ST_CH1) TEMP_SPAN) 2 2))
    )
    (PROGN
      
    (SETQ ST_CH1 (RTOS (- (+ (ATOF ST_CH1) TEMP_SPAN) 1000 ) 2 2))
    )
    )
    
    (SETQ I (+ I 1))

    
    )
)



(DEFUN GET_PROJECTION_FROM_POINT_LIST_PORTAL (LINE_ENTITY POINT_LIST FLAG  / VLA_LINE_ENTITY I TEMP_ELE FINAL_LIST)
(SETQ VLA_LINE_ENTITY (VLAX-ENAME->VLA-OBJECT LINE_ENTITY))
(SETQ I 0 TEMP_ELE NIL FINAL_LIST NIL)
(WHILE (< I (LENGTH POINT_LIST))
(SETQ TEMP_ELE (VLAX-CURVE-GETCLOSESTPOINTTO LINE_ENTITY (NTH FLAG (NTH I POINT_LIST)) T))
(SETQ FINAL_LIST (CONS (APPEND (NTH I POINT_LIST) (LIST TEMP_ELE)) FINAL_LIST))
(SETQ I (+ I 1))
)
(REVERSE FINAL_LIST)
)


(DEFUN SORT_MASTS (ENT_LIST STARTING_MAST / I TEMP_DIST FINAL_LIST )
  (SETQ TEMP_MAST (ASSOC STARTING_MAST ENT_LIST))
  (SETQ I 0 TEMP_DIST NIL FINAL_LIST NIL)
  (WHILE (< I (LENGTH ENT_LIST))
    (SETQ TEMP_DIST (DISTANCE (NTH 1 TEMP_MAST) (NTH 1 (NTH I ENT_LIST))))
    (SETQ FINAL_LIST (CONS (APPEND (NTH I ENT_LIST) (LIST TEMP_DIST)) FINAL_LIST))
    (SETQ I (+ I 1))
  )
  (SORT_FUN (REVERSE FINAL_LIST) 0 2)
)


(DEFUN C:UPDATE_CHAINAGES_MASTS_YARD (/	      SSSET
			      LOC_NO	      ST_CH
			      ENT_LIST	      BS_PT
			      ENT_INFO	      VALUES
			      VALUES1	      VALUES2
			      VALUES3	      VALUES4
			      FDN_REFERENCE   FDN_REFERENCE_X
			      FDN_REFERENCE_Y RD_REFERENCE
			      RD_REFERENCE_X  RD_REFERENCE_Y
			      TC_REFERENCE    TC_REFERENCE_X
			      TC_REFERENCE_Y  SPAN_REFERENCE_X
			      SPAN_REFERENCE_Y
			      ENT_LIST_SPAN   POINT
			      POINT1	      POINT2
			      POINT3	      ENT_LIST_SPAN
			      VISIBILITY_SPAN VISIBILITY_TC
			      VISIBILITY_FDN  VISIBILITY_RD
			      I		      LOC
			      CH	      TEMP_ELE
			      SCALE	      POINT_FDN
			      POINT_RD	      POINT_TC
			      TEMP_SPAN
			     )
  (PROMPT "\n SELECT MASTS")
  (SETQ SSSET (SSGET))
  (SETQ STARTING_MAST (CAR(ENTSEL "N/ SELECT STARTING MAST")))
  (SETQ TRACK_CENTER (CAR(ENTSEL "N/ SELECT TRACK CENTER")))
  (SETQ LOC_NO (GETSTRING "\n ENTER STARTING MAST LOCATION NUMBER :"))
  (SETQ ST_CH (GETSTRING "\n ENTER STARTING MAST CHAINAGE (CONTINUOUS) :"))
  (SETQ ST_CH1 (GETSTRING "\n ENTER STARTING MAST CHAINAGE (DFCC) :"))
  

  
  (COMMAND "UCS" "W")
  (SETQ KM_NO (SUBSTR LOC_NO 1 (VL-STRING-POSITION (ASCII "/") LOC_NO)))
  (SETQ	LOC_NO (SUBSTR LOC_NO
		       (+ (VL-STRING-POSITION (ASCII "/") LOC_NO) 2)
	       )
  )
  (SETQ
    ST_CH (SUBSTR ST_CH (+ (VL-STRING-POSITION (ASCII "/") ST_CH) 2))
  )

  (SETQ	KM_NO1	(SUBSTR	ST_CH1 1 (VL-STRING-POSITION (ASCII "/") ST_CH1)))
  (SETQ	ST_CH1	(SUBSTR	ST_CH1 (+ (VL-STRING-POSITION (ASCII "/") ST_CH1) 2)))

  (SETQ	ENT_LIST (SINGLE_ELE_LIST
		   (FILTER_LIST
		     (LIST "SINGLE_CANT_MAST" "DOUBLE_CANT_MAST" "TRIPLE_CANT_MAST" "SS0" "SS1" "SS2" "SS3")
		     (EXTRACT_ENTITY_INFO2 (FORM_SSSET SSSET))
		     1
		   )
		   0
		 )
  )
  (SETQ ENT_LIST (EXTRACT_ENTITY_INFO ENT_LIST 1 3))
  
  (SETQ ENT_LIST (SORT_MASTS ENT_LIST STARTING_MAST))
  (SETQ ENT_LIST (GET_PROJECTION_FROM_POINT_LIST_PORTAL TRACK_CENTER ENT_LIST 1))
  (SETQ ENT_LIST (BUILD_LIST ENT_LIST (LIST 0 3)))


 
  (SETQ I 0)
  
  
  (WHILE (< I (LENGTH ENT_LIST))
    (SETQ LOC (STRCAT KM_NO "/" LOC_NO))
    (SETQ CH (STRCAT KM_NO "/" ST_CH))
    
    
    (SETQ CH1 (STRCAT KM_NO1 "/" ST_CH1))
    

    (SETQ TEMP_ELE (NTH I ENT_LIST))
    
    
    (MODIFY_ATTRIBUTES
      (NTH 0 TEMP_ELE)
      (LIST "CHAINAGE1")
      (LIST  CH)
    )

    (MODIFY_ATTRIBUTES
      (NTH 0 TEMP_ELE)
      (LIST "CHAINAGE2")
      (LIST CH1)
    )


    (IF (/= (NTH (+ I 1) ENT_LIST) NIL) (SETQ TEMP_SPAN (DISTANCE_ON_CURVE_GPS TRACK_CENTER (NTH 1 TEMP_ELE) (NTH 1 (NTH (+ I 1) ENT_LIST)))))

    (IF (<= (+ (ATOF ST_CH) TEMP_SPAN) 1000)
    (PROGN
    (SETQ ST_CH (RTOS (+ (ATOF ST_CH) TEMP_SPAN) 2 2))
    )

    (PROGN
    (SETQ LOC_NO "1" LOC_NO_DN "2" KM_NO (RTOS (+ (ATOF KM_NO) 1) 2 0))
    (SETQ ST_CH (RTOS (- (+ (ATOF ST_CH) TEMP_SPAN) 1000 ) 2 2))
    )
      
    )

    (IF (<= (+ (ATOF ST_CH1) TEMP_SPAN) 1000)
    (PROGN
    (SETQ ST_CH1 (RTOS (+ (ATOF ST_CH1) TEMP_SPAN) 2 2))
    )
    (PROGN
    (SETQ KM_NO1 (RTOS (+ (ATOF KM_NO1) 1) 2 0))  
    (SETQ ST_CH1 (RTOS (- (+ (ATOF ST_CH1) TEMP_SPAN) 1000 ) 2 2))
    )
    )
    
    

    
    (SETQ I (+ I 1))
  )
  
  (COMMAND "UCS" "P")
)








(DEFUN C:UPDATE_HRL_YARD( / TOTAL_LIST LIST1 ENT_LIST I BLOCK_LIST FILTERED_LIST TEMP_LIST LOC_DETAILS PER)
(SETQ WPT1 (GETPOINT "ENTER STARTING POINT IN LOP"))
(SETQ WPT2 (GETPOINT "\n ENTER ENDING POINT IN LOP"))
(SETQ FILTERED_LIST (YARD_DATA_COLLECT WPT1 WPT2 '("SINGLE_CANT_MAST" "DOUBLE_CANT_MAST" "TRIPLE_CANT_MAST" "TTC" "SS1" "SS2" "SS3" "SS4" "PORTAL" "SS5") 1 3))
(SETQ TRACK_ENTITY_UPTRACK (ENTSEL "\nSELECT TRACK ALIGNMENT FOR UP TRACK (DN LINE):"))
(SETQ STRUCTURE_ENTITIES (YARD_DATA_COLLECT WPT1 WPT2 '("SINGLE_CANT_MAST" "DOUBLE_CANT_MAST" "TRIPLE_CANT_MAST" "TTC" "SS1" "SS2" "SS3" "SS4" "PORTAL" "SS5") 1 3))
(SETQ REF_MAST_DN (CAR (ENTSEL "\nSELECT REFERENCE MAST DNLINE:")))
(SETQ REF_MAST_UP (CAR (ENTSEL "\nSELECT REFERENCE MAST UPLINE:")))
(SETQ ATTRIBUTE_TAG_LIST (LIST "FOUNDATION_TYPE1" "RD1" "STEP_DISTANCE/EMBEDDED_LENGTH" "SUPER_BLOCK/EXTRA_DEPTH" "RADIUS/SUPER_ELEVATION" "DUMMY_VARIABLE2" "ANCHOR_BLOCK/ANCHOR_STEP/ANCHOR_SETTING_DISTANCE")) 

  (SETQ I 0)
  (SETQ PER (/ (* (+ I 1) 100) (LENGTH FILTERED_LIST)))
  (SETQ TEMP_LIST NIL)
  (SETQ LOC_DETAILS NIL)
  
  (WHILE (< I (LENGTH FILTERED_LIST))

    (IF (/= (NTH I FILTERED_LIST) NIL)
    (PROGN
    
    
    
    (SETQ LOC_NUMBER (NTH 0 (SINGLE_ELE_LIST (EXTRACT_ATTRIBUTES (NTH 0 (NTH I FILTERED_LIST)) (LIST "MAST_NUMBER1" ) 1) 1)))
    

    (PUTCELLSHEET "Implantation" "B7" (LIST LOC_NUMBER))
    
    (SETQ LOC_DETAILS (PARAMETERS_EXTRACT "Implantation" "B6:B7" "C6:C7"))
    (SETQ LOC_DETAILS (SINGLE_ELE_LIST LOC_DETAILS 1))   
    (MODIFY_ATTRIBUTES (NTH 0 (NTH I FILTERED_LIST)) (lIST "DUMMY_VARIABLE2" "DUMMY_VARIABLE6") (LIST (NTH 1 LOC_DETAILS) (NTH 1 LOC_DETAILS)))
    ;(MODIFY_ATTRIBUTES (NTH 0 (NTH I FILTERED_LIST)) (lIST "RD1") (LIST (RTOS (NTH 1 LOC_DETAILS) 2 0)))
    
    )
    )
    (SETQ I (+ I 1))
    
    )
  

     
)




(DEFUN C:PRINT_LOC_DETAILS_YARDS ( / )
   (SETQ BLOCKS_LIST (FORM_SSSET (SSGET "X" (LIST (CONS 0 "INSERT")))))
   (SETQ BLOCK_NAME_LIST (EXTRACT_ENTITY_INFO2 BLOCKS_LIST))
   (SETQ ENT_LIST (SINGLE_ELE_LIST (FILTER_LIST (LIST "SINGLE_CANT_MAST" "DOUBLE_CANT_MAST" "TRIPLE_CANT_MAST" "TTC" "SS1" "SS2" "SS3" "SS4" "PORTAL" "SS5") BLOCK_NAME_LIST 1) 0))
   (SETQ STARTING_MAST (CAR(ENTSEL "N/ SELECT STARTING MAST")))
   (SETQ TRACK_CENTER (CAR(ENTSEL "N/ SELECT TRACK CENTER")))
   (SETQ STARTING_CELL (GETSTRING "N/ ENTER STARTING CELL"))
   ;(SETQ ENT_LIST (FORM_SSSET SSSET))
   (SETQ ENT_LIST (EXTRACT_ENTITY_INFO ENT_LIST 1 3))
   (SETQ ENT_LIST (SORT_MASTS ENT_LIST STARTING_MAST))
    (SETQ DETAILS_TO_PRINT (GET_LOC_DETAILS_YARD (SINGLE_ELE_LIST ENT_LIST 0)))
    (PUTCELLSHEET "Sheet1" (COLUMN+N STARTING_CELL 0) (SINGLE_ELE_LIST DETAILS_TO_PRINT 0))
    (PUTCELLSHEET "Sheet1" (COLUMN+N STARTING_CELL 1) (SINGLE_ELE_LIST DETAILS_TO_PRINT 1))

)



(DEFUN C:LOAD_EXCEL_GPS ( / )
  (OPENEXCEL (FINDFILE "SPANEXTRACT.XLSX") "Sheet1" T)
)

(DEFUN C:LOAD_OBSTRUCTION_FILE ( / )
  (OPENEXCEL (FINDFILE (GETFILED "SELECT OBSTRUCTION FILE" "" "" 8)) "Sheet1" T)
)

(DEFUN GET_LOC_DETAILS_YARD ( ENT_LIST  / ENT_LIST I TEMP_CHAINAGE TEMP_EFFNAME TEMP_SPAN FINAL_LIST)

  (SETQ I 0 TEMP_CHAINAGE NIL TEMP_EFFNAME NIL TEMP_SPAN NIL FINAL_LIST NIL)
  (WHILE (< I (LENGTH ENT_LIST))

    (IF (/= (VL-POSITION (VLAX-GET-PROPERTY (VLAX-ENAME->VLA-OBJECT (NTH I ENT_LIST)) 'EFFECTIVENAME) (LIST "PORTAL" "SS5")) NIL)
    (PROGN
    (SETQ TEMP_NUMBER (NTH 0 (SINGLE_ELE_LIST (EXTRACT_ATTRIBUTES (NTH I ENT_LIST) (LIST "MAST_NUMBER1" ) 1) 1)))
    (SETQ TEMP_CHAINAGE (NTH 0 (SINGLE_ELE_LIST (EXTRACT_ATTRIBUTES (NTH I ENT_LIST) (LIST "CHAINAGE3" ) 1) 1)))
    )
    (PROGN
    (SETQ TEMP_NUMBER (NTH 0 (SINGLE_ELE_LIST (EXTRACT_ATTRIBUTES (NTH I ENT_LIST) (LIST "MAST_NUMBER1" ) 1) 1)))
    (SETQ TEMP_CHAINAGE (NTH 0 (SINGLE_ELE_LIST (EXTRACT_ATTRIBUTES (NTH I ENT_LIST) (LIST "CHAINAGE2" ) 1) 1)))
    )
    )
    (SETQ FINAL_LIST (CONS (LIST TEMP_NUMBER (CONVERT_CHAINAGE_TO_NUMBER TEMP_CHAINAGE)) FINAL_LIST))

    (SETQ I (+ I 1))
  )

  (REVERSE FINAL_LIST)
  
)


(DEFUN CONVERT_CHAINAGE_TO_NUMBER ( CHAINAGE  / KM  CHAINAGE )
  
    (IF (/= (VL-STRING-POSITION (ASCII "/") CHAINAGE) NIL)
    (PROGN
    (SETQ KM (SUBSTR CHAINAGE 1 (VL-STRING-POSITION (ASCII "/") CHAINAGE)))
    (SETQ CHAINAGE (SUBSTR CHAINAGE (+ (VL-STRING-POSITION (ASCII "/") CHAINAGE) 2)))
    (SETQ KM (* (ATOF KM) 1000))
    (SETQ CHAINAGE (* (ATOF CHAINAGE) 1))
    (+ KM CHAINAGE)
    )
    )
)



(DEFUN C:PRINT_PORTAL_TYPES ( / )
   (SETQ BLOCKS_LIST (FORM_SSSET (SSGET "X" (LIST (CONS 0 "INSERT")))))
   (SETQ BLOCK_NAME_LIST (EXTRACT_ENTITY_INFO2 BLOCKS_LIST))
   (SETQ ENT_LIST (SINGLE_ELE_LIST (FILTER_LIST (LIST "PORTAL" "SS5") BLOCK_NAME_LIST 1) 0))
   (SETQ STARTING_MAST (CAR(ENTSEL "N/ SELECT STARTING MAST")))
   (SETQ TRACK_CENTER (CAR(ENTSEL "N/ SELECT TRACK CENTER")))
   (SETQ STARTING_CELL (GETSTRING "N/ ENTER STARTING CELL"))
   ;(SETQ ENT_LIST (FORM_SSSET SSSET))
   (SETQ ENT_LIST (EXTRACT_ENTITY_INFO ENT_LIST 1 3))
   (SETQ ENT_LIST (SORT_MASTS ENT_LIST STARTING_MAST))
    (SETQ DETAILS_TO_PRINT (GET_PORTAL_TYPES (SINGLE_ELE_LIST ENT_LIST 0)))
    (PUTCELLSHEET "Sheet1" (COLUMN+N STARTING_CELL 0) (SINGLE_ELE_LIST DETAILS_TO_PRINT 0))
    (PUTCELLSHEET "Sheet1" (COLUMN+N STARTING_CELL 1) (SINGLE_ELE_LIST DETAILS_TO_PRINT 1))

)



(DEFUN GET_PORTAL_TYPES( ENT_LIST  / ENT_LIST I TEMP_CHAINAGE TEMP_EFFNAME TEMP_SPAN FINAL_LIST)

  (SETQ I 0 TEMP_CHAINAGE NIL TEMP_EFFNAME NIL TEMP_SPAN NIL FINAL_LIST NIL)
  (WHILE (< I (LENGTH ENT_LIST))

    (IF (/= (VL-POSITION (VLAX-GET-PROPERTY (VLAX-ENAME->VLA-OBJECT (NTH I ENT_LIST)) 'EFFECTIVENAME) (LIST "PORTAL" "SS5")) NIL)
    (PROGN
    (SETQ TEMP_TYPE (NTH 0 (SINGLE_ELE_LIST (EXTRACT_ATTRIBUTES (NTH I ENT_LIST) (LIST "MAST_TYPE1" ) 1) 1)))
    (SETQ TEMP_CS (NTH 0 (SINGLE_ELE_LIST (EXTRACT_ATTRIBUTES (NTH I ENT_LIST) (LIST "CS1" ) 1) 1)))
    )
    
    )
    (SETQ FINAL_LIST (CONS (LIST TEMP_TYPE TEMP_CS) FINAL_LIST))

    (SETQ I (+ I 1))
  )

  (REVERSE FINAL_LIST)
  
)
