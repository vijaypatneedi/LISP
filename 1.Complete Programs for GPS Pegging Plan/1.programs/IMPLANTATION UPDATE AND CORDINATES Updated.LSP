(DEFUN MAP_NEAREST_SUPERMAST (LIST1 PT K / I TEMP_SET LIST2)
  (SETQ I 0)
  (SETQ TEMP_SET NIL)
  (SETQ LIST2 NIL)
  (WHILE (< I (LENGTH LIST1))

    (IF	(NOT (ATOM (NTH K (NTH I LIST1))))
      (PROGN (SETQ TEMP_SET
		    (LIST
		      (ABS (DISTANCE2D (NTH K (NTH I LIST1)) PT))
		      (NTH I LIST1)
		    )
	     )
	     (SETQ LIST2 (CONS TEMP_SET LIST2))
      )
      (PROGN (SETQ TEMP_SET (LIST (ABS (DISTANCE2D (NTH I LIST1) PT))
				  (NTH I LIST1)
			    )
	     )
	     (SETQ LIST2 (CONS TEMP_SET LIST2))
      )
    )



    (SETQ I (+ I 1))
  )
  
  (SETQ FINAL_ELE (NTH 0 (SORT_FUN LIST2 0 0)))
  (IF (< (NTH 0 FINAL_ELE) 1) (NTH 1 FINAL_ELE) (LIST NIL))
)


(DEFUN DATA_TO_STRUCTURE_MAP_SUPERMAST
       (LIST1 LIST2 K Q / I TEMP_ELE TEMP_ELE1 LIST3)
  (SETQ I 0)
  (SETQ TEMP_ELE NIL)
  (SETQ TEMP_ELE1 NIL)
  (SETQ LIST3 NIL)
  (WHILE (< I (LENGTH LIST1))
    (SETQ TEMP_ELE1 (MAP_NEAREST_SUPERMAST LIST2 (NTH K (NTH I LIST1)) Q))
    (SETQ TEMP_ELE (APPEND (LIST (NTH 0 (NTH I LIST1))) TEMP_ELE1))
    (SETQ LIST3 (CONS TEMP_ELE LIST3))
    (SETQ LIST2 (VL-REMOVE TEMP_ELE1 LIST2))
    (SETQ I (+ I 1))
  )
  LIST3
)



(DEFUN GET_TOTAL_LOC_LIST_GPS (/)


  (SETQ WPT1 (GETPOINT "\n ENTER STARTING POINT IN LOP:"))
  (SETQ WPT2 (GETPOINT "\n ENTER ENDING POINT IN LOP:"))
  (SETQ BLOCKS_LIST (FORM_SSSET (SSGET "X" (LIST (CONS 0 "INSERT")))))
  (SETQ	MAST_ENTITIES
	 (YARD_DATA_COLLECT_GPS
	   BLOCKS_LIST
	   '("SINGLE_CANT_MAST"	"DOUBLE_CANT_MAST" "TRIPLE_CANT_MAST"
	     "SS0"		"SS1"		   "SS2"
	     "SS3"
	    )
	   1
	   5
	 )
  )
  (SETQ UPLINE_MAST_ENTITIES (FILTER_LIST '("DN") MAST_ENTITIES 1))
  (SETQ DNLINE_MAST_ENTITIES (FILTER_LIST '("UP") MAST_ENTITIES 1))
  (SETQ	UPLINE_MAST_ENTITIES
	 (EXTRACT_ENTITY_INFO
	   (SINGLE_ELE_LIST UPLINE_MAST_ENTITIES 0)
	   1
	   3
	 )
  )
  (SETQ	DNLINE_MAST_ENTITIES
	 (EXTRACT_ENTITY_INFO
	   (SINGLE_ELE_LIST DNLINE_MAST_ENTITIES 0)
	   1
	   3
	 )
  )
  (SETQ	MAST_E (YARD_DATA_COLLECT_GPS
		 BLOCKS_LIST
		 '("SINGLE_CANT_MAST" "DOUBLE_CANT_MAST"
		   "TRIPLE_CANT_MAST" "SS0"
		   "SS1"	      "SS2"
		   "SS3"
		  )
		 1
		 3
	       )
  )
  (SETQ	ANCHOR_LIST
	 (YARD_DATA_COLLECT_GPS BLOCKS_LIST '("ANCHOR" "BTB_ANC") 1 3)
  )
  (SETQ SM_LIST (YARD_DATA_COLLECT_GPS BLOCKS_LIST '("SUPER_MAST") 1 3))
  (SETQ	ANCHOR_STRUCTURE_MAP_DATA
	 (DATA_TO_STRUCTURE_MAP1
	   ANCHOR_LIST
	   MAST_E
	   1
	   1
	 )
  )
  (SETQ	SM_STRUCTURE_MAP_DATA
	 (DATA_TO_STRUCTURE_MAP_SUPERMAST SM_LIST MAST_E 1 1)
  )
  (SETQ	ANCHOR_STRUCTURE_MAP_DATA
	 (BUILD_LIST
	   ANCHOR_STRUCTURE_MAP_DATA
	   '(1 0)
	 )
  )
  (SETQ SM_STRUCTURE_MAP_DATA (BUILD_LIST SM_STRUCTURE_MAP_DATA '(1 0)))
  (SETQ	PAIRED_MASTS
	 (PAIR_MASTS
	   (SINGLE_ELE_LIST UPLINE_MAST_ENTITIES 0)
	   (SINGLE_ELE_LIST DNLINE_MAST_ENTITIES 0)
	 )
  )
  (SETQ	UPLINE_DATA
	 (APPEND_LISTS_M
	   (SINGLE_ELE_LIST PAIRED_MASTS 0)
	   SM_STRUCTURE_MAP_DATA
	   ANCHOR_STRUCTURE_MAP_DATA
	 )
  )
  (SETQ	DNLINE_DATA
	 (APPEND_LISTS_M
	   (SINGLE_ELE_LIST PAIRED_MASTS 1)
	   SM_STRUCTURE_MAP_DATA
	   ANCHOR_STRUCTURE_MAP_DATA
	 )
  )
  (ADD_LISTS1 UPLINE_DATA DNLINE_DATA)


)

(DEFUN C:UPDATE_IMPLANTATION ( / TOTAL_LIST LIST1 ENT_LIST I BLOCK_LIST FILTERED_LIST TEMP_LIST LOC_DETAILS PER)
(SETQ TOTAL_LIST (GET_TOTAL_LOC_LIST_GPS))
   (setq dcl_id (load_dialog "DISPLAY_INFO.dcl"))
   (new_dialog "DISPLAY_INFO" dcl_id)
  
   
(SETQ FILTERED_LIST (APPEND (SINGLE_ELE_LIST TOTAL_LIST 0) (SINGLE_ELE_LIST TOTAL_LIST 1)))
  (SETQ I 0)
  (SETQ PER (/ (* (+ I 1) 100) (LENGTH FILTERED_LIST)))
  (SETQ TEMP_LIST NIL)
  (SETQ LOC_DETAILS NIL)
  
  (WHILE (< I (LENGTH FILTERED_LIST))
    (SET_TILE "INFO" (STRCAT "UPDATING FOUNDATION" " " (ITOA (+ I 1)) " " "OF" " "  (ITOA (LENGTH FILTERED_LIST))))
    (SET_TILE "PERCENTAGE" (STRCAT (RTOS PER 2 2) "%" " " "COMPLETED"))
    (IF (/= (NTH I FILTERED_LIST) NIL)
    (PROGN
    (SETQ TEMP_LIST (GET_DATA_TO_BE_FILLED2 (NTH I FILTERED_LIST)))
    (PUTCELLSHEET "PROIN" "F8" (NTH 0 TEMP_LIST))
    ;NEWLYADDED
    (SETQ DFCC_CHAINAGE (NTH 0 (SINGLE_ELE_LIST (EXTRACT_ATTRIBUTES (NTH 0 (NTH I FILTERED_LIST)) (LIST "CHAINAGE2" ) 1) 1)))
    (SETQ KM (SUBSTR DFCC_CHAINAGE 1 (VL-STRING-POSITION (ASCII "/") DFCC_CHAINAGE)))
    (SETQ CHAINAGE (SUBSTR DFCC_CHAINAGE (+ (VL-STRING-POSITION (ASCII "/") DFCC_CHAINAGE) 2)))
    (PUTCELLSHEET "PROIN" "F8" KM)
    (PUTCELLSHEET "PROIN" "F10" CHAINAGE)
    ;
    (SETQ LOC_DETAILS (PARAMETERS_EXTRACT "Implantation" "A46:A46" "B46:B46"))
    (SETQ LOC_DETAILS (RTOS (NTH 0 (SINGLE_ELE_LIST LOC_DETAILS 1)) 2 2))
    (MODIFY_ATTRIBUTES (NTH 0 (NTH I FILTERED_LIST)) (lIST "IMPLANTATION1") (LIST LOC_DETAILS))
    (IF (= I (- (LENGTH FILTERED_LIST) 1)) (PROGN (SET_TILE "INFO" "FOUNDATIONS ARE UPDATED") (SET_TILE "PERCENTAGE" "CLICK OK TO VIEW RESULTS")))
    )
    )
    (SETQ I (+ I 1))
    (SETQ PER (/ (* (+ I 1) 100) (LENGTH FILTERED_LIST)))
    )
    (setq ddiag(start_dialog))
)




  
  



(DEFUN C:UPDATE_FOUNDATION ( / TOTAL_LIST LIST1 ENT_LIST I BLOCK_LIST FILTERED_LIST TEMP_LIST LOC_DETAILS PER)
(SETQ TOTAL_LIST (GET_TOTAL_LOC_LIST_GPS))
(SETQ BLOCKS_LIST (FORM_SSSET (SSGET "W" WPT1 WPT2 (LIST (CONS 0 "INSERT")))))
(SETQ TRACK_ENTITY_UPTRACK (ENTSEL "\nSELECT TRACK ALIGNMENT FOR UP TRACK (DN LINE):"))
(SETQ ATTRIBUTE_TAG "FOUNDATION_TYPE1")
  
  (SETQ REF_MAST_DN (CAR (ENTSEL "\nSELECT REFERENCE MAST DNLINE:")))
  (SETQ REF_MAST_UP (CAR (ENTSEL "\nSELECT REFERENCE MAST UPLINE:")))
  
   (setq dcl_id (load_dialog "DISPLAY_INFO.dcl"))
   (new_dialog "DISPLAY_INFO" dcl_id)
  
   
(SETQ FILTERED_LIST (APPEND (SINGLE_ELE_LIST TOTAL_LIST 0) (SINGLE_ELE_LIST TOTAL_LIST 1)))
  (SETQ I 0)
  (SETQ PER (/ (* (+ I 1) 100) (LENGTH FILTERED_LIST)))
  (SETQ TEMP_LIST NIL)
  (SETQ LOC_DETAILS NIL)
  
  (WHILE (< I (LENGTH FILTERED_LIST))
    (SET_TILE "INFO" (STRCAT "UPDATING FOUNDATION" " " (ITOA (+ I 1)) " " "OF" " "  (ITOA (LENGTH FILTERED_LIST))))
    (SET_TILE "PERCENTAGE" (STRCAT (RTOS PER 2 2) "%" " " "COMPLETED"))
    (IF (/= (NTH I FILTERED_LIST) NIL)
    (PROGN
    (SETQ TEMP_LIST (GET_DATA_TO_BE_FILLED2 (NTH I FILTERED_LIST)))
    (PUTCELLSHEET "PROIN" "F8" (NTH 0 TEMP_LIST))
    (SETQ DFCC_CHAINAGE (NTH 0 (SINGLE_ELE_LIST (EXTRACT_ATTRIBUTES (NTH 0 (NTH I FILTERED_LIST)) (LIST "CHAINAGE2" ) 1) 1)))
    
    (SETQ KM (SUBSTR DFCC_CHAINAGE 1 (VL-STRING-POSITION (ASCII "/") DFCC_CHAINAGE)))
    (SETQ CHAINAGE (SUBSTR DFCC_CHAINAGE (+ (VL-STRING-POSITION (ASCII "/") DFCC_CHAINAGE) 2)))
    
    (PUTCELLSHEET "PROIN" "F8" KM)
    (PUTCELLSHEET "PROIN" "F10" CHAINAGE)
    
    (SETQ LOC_DETAILS (PARAMETERS_EXTRACT "Implantation" "A17:A20" "B17:B20"))
    (SETQ LOC_DETAILS (SINGLE_ELE_LIST LOC_DETAILS 1))
    (MODIFY_ATTRIBUTES (NTH 0 (NTH I FILTERED_LIST)) (lIST "FOUNDATION_TYPE1" "RD1" "STEP_DISTANCE/EMBEDDED_LENGTH" "ANCHOR_BLOCK/ANCHOR_STEP/ANCHOR_SETTING_DISTANCE") LOC_DETAILS)
    (MODIFY_ATTRIBUTES (NTH 0 (NTH I FILTERED_LIST)) (lIST "RD1") (LIST (RTOS (NTH 1 LOC_DETAILS) 2 0)))
    (IF (= I (- (LENGTH FILTERED_LIST) 1)) (PROGN (SET_TILE "INFO" "FOUNDATIONS ARE UPDATED") (SET_TILE "PERCENTAGE" "CLICK OK TO VIEW RESULTS")))
    )
    )
    (SETQ I (+ I 1))
    (SETQ PER (/ (* (+ I 1) 100) (LENGTH FILTERED_LIST)))
    )
    (setq ddiag(start_dialog))
  (SETQ BLOCK_NAME_LIST (EXTRACT_ENTITY_INFO2 BLOCKS_LIST))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_UP (FILTER_LIST '("UP") MAST_TTC_DIR 1))
  (SETQ MAST_DN (FILTER_LIST '("DN") MAST_TTC_DIR 1))
  (SETQ TOTAL_LIST (SINGLE_ELE_LIST (APPEND MAST_UP MAST_DN) 0))
  ;(SETQ I 0)
  ;(WHILE (< I (LENGTH TOTAL_LIST))
  ;   (CHANGE_VISIBILITY (NTH I TOTAL_LIST) (LIST "FOUNDATION_TYPE1") (LIST "1"))
  ;    (SETQ  I (+ I 1))
  ;)
  ;(SETQ MAST_UP (SORT_ENTITIES_ALONG_CURVE1 (VLAX-ENAME->VLA-OBJECT (NTH 0 TRACK_ENTITY_UPTRACK)) MAST_UP (LIST 1 STARTING_POINT) 0 1))
  ;(SETQ MAST_DN (SORT_ENTITIES_ALONG_CURVE1 (VLAX-ENAME->VLA-OBJECT (NTH 0 TRACK_ENTITY_UPTRACK)) MAST_DN (LIST 1 STARTING_POINT) 0 1))

  (MATCH_POSITION1 REF_MAST_UP (SINGLE_ELE_LIST MAST_UP 0) ATTRIBUTE_TAG)
  (MATCH_POSITION1 REF_MAST_DN (SINGLE_ELE_LIST MAST_DN 0) ATTRIBUTE_TAG)
  
    
)



(DEFUN MATCH_POSITION1 (ENTNAME ENT_LIST ATTRIBUTE_TAG / ENTNAME SSSET ENT_LIST ENT_INFO MAST_NUMBER MAST_NUMBER_X MAST_NUMBER_Y FDN_REFERENCE FDN_REFERENCE_X FDN_REFERENCE_Y RD_REFERENCE RD_REFERENCE_X RD_REFERENCE_Y TC_REFERENCE TC_REFERENCE_X TC_REFERENCE_Y SPAN_REFERENCE_X SPAN_REFERENCE_Y BS_PT VALUES VALUES1 VALUES2 VALUES3 VALUES4 VALUES5 POINT POINT1 POINT2 POINT3 POINT4 POINT5 VISIBILITY_SPAN VISIBILITY_TC VISIBILITY_FDN VISIBILITY_RD I BASE_POINT TEMP_SPAN) 

  (COMMAND "UCS" "W")
  
  (SETQ ENT_LIST (EXTRACT_ENTITY_INFO ENT_LIST 1 3))
  (SETQ ENT_LIST (SORT_FUN ENT_LIST 1 0))
  (SETQ ENT_LIST (SINGLE_ELE_LIST ENT_LIST 0))

  (SETQ DFCC_CTN_CHAINAGE_REFERENCE (GET_TEXT_ALIGNMENT_POINT (LIST ENTNAME) ATTRIBUTE_TAG 0))
  (SETQ DFCC_CTN_CHAINAGE_REFERENCE_X (- (NTH 0 (NTH 1 (NTH 0 DFCC_CTN_CHAINAGE_REFERENCE))) (NTH 0 (CDR (ASSOC 10 (ENTGET ENTNAME))))))
  (SETQ DFCC_CTN_CHAINAGE_REFERENCE_Y (- (NTH 1 (NTH 1 (NTH 0 DFCC_CTN_CHAINAGE_REFERENCE))) (NTH 1 (CDR (ASSOC 10 (ENTGET ENTNAME))))))

  (SETQ REFERENCE_LIST1 (LIST (LIST DFCC_CTN_CHAINAGE_REFERENCE_X DFCC_CTN_CHAINAGE_REFERENCE_Y 0.0)))
  ;(SETQ BS_PT (CDR (ASSOC 10 (ENTGET ENTNAME))))

  (SETQ BASE_ROTATION (VLAX-GET-PROPERTY (VLAX-ENAME->VLA-OBJECT ENTNAME) 'ROTATION))

  (SETQ I 0 BASE_POINT NIL ROTATION NIL TEMP_IMPLANTATION NIL TEMP_POINT_LIST NIL )
  (WHILE (< I (LENGTH ENT_LIST))
    
    (SETQ BASE_POINT (CDR (ASSOC 10 (ENTGET (NTH I ENT_LIST)))))
    (SETQ ROTATION (VLAX-GET-PROPERTY (VLAX-ENAME->VLA-OBJECT (NTH I ENT_LIST)) 'ROTATION))
    (SETQ TEMP_IMPLANTATION (ATOF (NTH 0 (SINGLE_ELE_LIST (EXTRACT_ATTRIBUTES (NTH I ENT_LIST) (LIST "IMPLANTATION1" ) 1) 1))))
    
    (SETQ TEMP_POINT_LIST1 (TRANSFORM_ADJ REFERENCE_LIST1 BASE_POINT (-  ROTATION BASE_ROTATION) (- 3.00 3.00)))

    (CHANGE_TEXT_ALIGNMENT_POINT (NTH I ENT_LIST) (LIST ATTRIBUTE_TAG) (LIST (NTH 0 TEMP_POINT_LIST1)))

    (SETQ I (+ I 1))
  )
  (COMMAND "UCS" "P")
  )




(DEFUN GET_SPAN_DETAILS ( ENT_LIST  / ENT_LIST I TEMP_CHAINAGE TEMP_EFFNAME TEMP_SPAN FINAL_LIST)

  (SETQ ENT_LIST (EXTRACT_ENTITY_INFO ENT_LIST 1 3))
  (SETQ ENT_LIST (SORT_FUN ENT_LIST 1 0))
  (SETQ ENT_LIST (SINGLE_ELE_LIST ENT_LIST 0))
  (SETQ I 0 TEMP_CHAINAGE NIL TEMP_EFFNAME NIL TEMP_SPAN NIL FINAL_LIST NIL)
  (WHILE (< I (LENGTH ENT_LIST))
    (SETQ TEMP_CHAINAGE (NTH 0 (SINGLE_ELE_LIST (EXTRACT_ATTRIBUTES (NTH I ENT_LIST) (LIST "MAST_NUMBER1" ) 1) 1)))
    (SETQ TEMP_CHAINAGE (NTH 0 (SINGLE_ELE_LIST (EXTRACT_ATTRIBUTES (NTH I ENT_LIST) (LIST "CHAINAGE1" ) 1) 1)))
    (SETQ TEMP_EFFNAME (VLAX-GET-PROPERTY (VLAX-ENAME->VLA-OBJECT (NTH I ENT_LIST)) 'EFFECTIVENAME))
    (SETQ TEMP_SPAN (NTH 0 (SINGLE_ELE_LIST (EXTRACT_ATTRIBUTES (NTH I ENT_LIST) (LIST "SPAN1" ) 1) 1)))
    (SETQ TEMP_MAST1 (NTH 0 (SINGLE_ELE_LIST (EXTRACT_ATTRIBUTES (NTH I ENT_LIST) (LIST "MAST_TYPE1" ) 1) 1)))
    (SETQ TEMP_MAST2 (NTH 0 (SINGLE_ELE_LIST (EXTRACT_ATTRIBUTES (NTH I ENT_LIST) (LIST "MAST_TYPE2" ) 1) 1)))
    (SETQ FINAL_LIST (CONS (LIST TEMP_CHAINAGE TEMP_EFFNAME TEMP_SPAN) FINAL_LIST))
    (SETQ I (+ I 1))
  )
  (REVERSE FINAL_LIST)
)










(DEFUN SORT_MASTS (ENT_LIST STARTING_MAST / I TEMP_DIST FINAL_LIST )
  (SETQ TEMP_MAST (ASSOC STARTING_MAST ENT_LIST))
  (SETQ I 0 TEMP_DIST NIL FINAL_LIST NIL)
  (WHILE (< I (LENGTH ENT_LIST))
    (SETQ TEMP_DIST (DISTANCE (NTH 1 TEMP_MAST) (NTH 1 (NTH I ENT_LIST))))
    (SETQ FINAL_LIST (CONS (APPEND (NTH I ENT_LIST) (LIST TEMP_DIST)) FINAL_LIST))
    (SETQ I (+ I 1))
  )
  (SORT_FUN (REVERSE FINAL_LIST) 0 2)
)





(DEFUN C:LOAD_EXCEL_GPS ( / )
  (OPENEXCEL (FINDFILE "SPANEXTRACT.XLSX") "Sheet1" T)
)







(DEFUN C:PRINT_LOC_DETAILS ( / )
   (SETQ BLOCKS_LIST (FORM_SSSET (SSGET "X" (LIST (CONS 0 "INSERT")))))
   (SETQ BLOCK_NAME_LIST (EXTRACT_ENTITY_INFO2 BLOCKS_LIST))
   (SETQ ENT_LIST (SINGLE_ELE_LIST (FILTER_LIST (LIST "SINGLE_CANT_MAST" "DOUBLE_CANT_MAST" "TRIPLE_CANT_MAST" "TTC" "SS0" "SS1" "SS2" "SS3" "SS4") BLOCK_NAME_LIST 1) 0))
   (SETQ STARTING_MAST (CAR(ENTSEL "N/ SELECT STARTING MAST")))
   (SETQ TRACK_CENTER (CAR(ENTSEL "N/ SELECT TRACK CENTER")))
   (SETQ STARTING_CELL (GETSTRING "N/ ENTER STARTING CELL"))
   ;(SETQ ENT_LIST (FORM_SSSET SSSET))
   (SETQ ENT_LIST (EXTRACT_ENTITY_INFO ENT_LIST 1 3))
   (SETQ ENT_LIST (SORT_MASTS ENT_LIST STARTING_MAST))
    (SETQ DETAILS_TO_PRINT (GET_CO-ORDINATES (SINGLE_ELE_LIST ENT_LIST 0)))
    (PUTCELLSHEET "Sheet1" (COLUMN+N STARTING_CELL 0) (SINGLE_ELE_LIST DETAILS_TO_PRINT 0))
    (PUTCELLSHEET "Sheet1" (COLUMN+N STARTING_CELL 1) (SINGLE_ELE_LIST DETAILS_TO_PRINT 1))
    (PUTCELLSHEET "Sheet1" (COLUMN+N STARTING_CELL 2) (SINGLE_ELE_LIST DETAILS_TO_PRINT 2))
    (PUTCELLSHEET "Sheet1" (COLUMN+N STARTING_CELL 3) (SINGLE_ELE_LIST DETAILS_TO_PRINT 3))
    (PUTCELLSHEET "Sheet1" (COLUMN+N STARTING_CELL 4) (SINGLE_ELE_LIST DETAILS_TO_PRINT 4))
    (PUTCELLSHEET "Sheet1" (COLUMN+N STARTING_CELL 5) (SINGLE_ELE_LIST DETAILS_TO_PRINT 5))
)



(DEFUN C:LOAD_EXCEL_GPS ( / )
  (OPENEXCEL (FINDFILE "SPANEXTRACT.XLSX") "Sheet1" T)
)

(DEFUN C:LOAD_OBSTRUCTION_FILE ( / )
  (OPENEXCEL (FINDFILE (GETFILED "SELECT OBSTRUCTION FILE" "" "" 8)) "Sheet1" T)
)

(DEFUN GET_CO-ORDINATES ( ENT_LIST  / ENT_LIST I TEMP_CHAINAGE TEMP_EFFNAME TEMP_SPAN FINAL_LIST)

  (SETQ I 0 TEMP_CHAINAGE NIL TEMP_EFFNAME NIL TEMP_SPAN NIL FINAL_LIST NIL)
  (WHILE (< I (LENGTH ENT_LIST))
    (SETQ TEMP_NUMBER (NTH 0 (SINGLE_ELE_LIST (EXTRACT_ATTRIBUTES (NTH I ENT_LIST) (LIST "MAST_NUMBER1" ) 1) 1)))
    (SETQ TEMP_CHAINAGE (NTH 0 (SINGLE_ELE_LIST (EXTRACT_ATTRIBUTES (NTH I ENT_LIST) (LIST "CHAINAGE1" ) 1) 1)))
    (SETQ TEMP_MAST (NTH 0 (SINGLE_ELE_LIST (EXTRACT_ATTRIBUTES (NTH I ENT_LIST) (LIST "MAST_TYPE1" ) 1) 1)))
    (SETQ TEMP_IMP (NTH 0 (SINGLE_ELE_LIST (EXTRACT_ATTRIBUTES (NTH I ENT_LIST) (LIST "IMPLANTATION1" ) 1) 1)))
    (SETQ TEMP_EFFNAME (VLAX-GET-PROPERTY (VLAX-ENAME->VLA-OBJECT (NTH I ENT_LIST)) 'EFFECTIVENAME))
    (SETQ TEMP_SPAN (NTH 0 (SINGLE_ELE_LIST (EXTRACT_ATTRIBUTES (NTH I ENT_LIST) (LIST "SPAN1" ) 1) 1)))
    
    (SETQ FLIP (NTH 1 (NTH 0 (GET_DYNAMIC_PROPERTIES (NTH I ENT_LIST) '("STF1")))))
    
    (SETQ ROTATION (VLAX-GET-PROPERTY (VLAX-ENAME->VLA-OBJECT (NTH I ENT_LIST)) 'ROTATION))
    (SETQ TEMP_CO-ORDINATES (CDR (ASSOC 10 (ENTGET (NTH I ENT_LIST)))))
    (IF (= FLIP 0)
     (SETQ TEMP_CO-ORDINATES (MAPCAR 'RTOS (POLAR TEMP_CO-ORDINATES (+ (* 1 (/ PI 2)) ROTATION) (+ (- (ATOF TEMP_IMP) 3.00) 0.2))) TEMP_LINE "Dn Line")
     (SETQ TEMP_CO-ORDINATES (MAPCAR 'RTOS (POLAR TEMP_CO-ORDINATES (+ (* 3 (/ PI 2)) ROTATION) (+ (- (ATOF TEMP_IMP) 3.00) 0.2))) TEMP_LINE "Up Line")
    )
    (SETQ FINAL_LIST (CONS (APPEND (LIST TEMP_NUMBER TEMP_CHAINAGE TEMP_MAST TEMP_IMP TEMP_SPAN TEMP_LINE) TEMP_CO-ORDINATES) FINAL_LIST))
    (SETQ I (+ I 1))
  )
  (REVERSE FINAL_LIST)
  
)



(DEFUN C:PRINT_GLOBAL_COORDINATES ( / )
  (SETQ WPT1 (GETPOINT "\n ENTER 1ST POINT OF POLYGON"))
  (SETQ WPT2 (GETPOINT "\n ENTER 2ND POINT OF POLYGON"))
  (SETQ WPT3 (GETPOINT "\n ENTER 3RD POINT OF POLYGON"))
  (SETQ WPT4 (GETPOINT "\n ENTER 4TH POINT OF POLYGON"))
  (SETQ BLOCKS_LIST (FORM_SSSET (SSGET "WP" (LIST WPT1 WPT2 WPT3 WPT4) (LIST (CONS 0 "INSERT")))))

  (SETQ STARTING_CELL (GETSTRING "\nEnter starting cell"))
  
  ;(SETQ BLOCKS_LIST (FORM_SSSET (SSGET "X" (LIST (CONS 0 "INSERT")))))
  (SETQ TRACK_ENTITY_UPTRACK (CAR(ENTSEL "\nSELECT TRACK ALIGNMENT FOR UP TRACK (DN LINE):")))
  (SETQ TRACK_ENTITY_DNTRACK (CAR(ENTSEL "\nSELECT TRACK ALIGNMENT FOR DN TRACK (UP LINE):")))
  (SETQ STARTING_POINT (GETPOINT "\nENTER STARTING POINT FOR UP TRACK (DN LINE):"))
  (SETQ STARTING_POINT_DN (GETPOINT "\nENTER STARTING POINT FOR DN TRACK (UP LINE):"))
  (SETQ BLOCK_NAME_LIST (EXTRACT_ENTITY_INFO2 BLOCKS_LIST))
  (SETQ ACC_LIST (FILTER_LIST (LIST "ACC") BLOCK_NAME_LIST 1))
  (SETQ OLC_LIST (FILTER_LIST (LIST "OLC") BLOCK_NAME_LIST 1))
  (SETQ TL_LIST (FILTER_LIST (LIST "TENSION_LENGTH") BLOCK_NAME_LIST 1))
  (SETQ ACC_LIST (BUILD_LIST (ENTITY_DFX (SINGLE_ELE_LIST ACC_LIST 0) 10 -1) (LIST 0 1)))
  (SETQ OLC_LIST (BUILD_LIST (ENTITY_DFX (SINGLE_ELE_LIST OLC_LIST 0) 10 -1) (LIST 0 1)))
  (SETQ TL_LIST  (BUILD_LIST (ENTITY_DFX (SINGLE_ELE_LIST TL_LIST 0)  10 -1) (LIST 0 1)))
  ;(COMMAND "BURST" (ENTLAST))
  (SETQ MAST_TTC (YARD_DATA_COLLECT_GPS BLOCKS_LIST '("SINGLE_CANT_MAST" "DOUBLE_CANT_MAST" "TRIPLE_CANT_MAST" "TTC" "SS0" "SS1" "SS2" "SS3" "SS4") 1 3))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  ;(SETQ ANCHOR_LIST (YARD_DATA_COLLECT WPT1 WPT2 '("ANCHOR") 1 3))
 (SETQ ANCHOR_ENTITIES (YARD_DATA_COLLECT_GPS BLOCKS_LIST '("ANCHOR") 1 5))
 (SETQ BTB_ANCHOR_ENTITIES (YARD_DATA_COLLECT_GPS BLOCKS_LIST '("BTB_ANC") 1 3))
 (SETQ ANCHOR_START (FILTER_LIST '("START") ANCHOR_ENTITIES 1))
 (SETQ ANCHOR_END (FILTER_LIST '("END") ANCHOR_ENTITIES 1))
 (SETQ MULTIPLE_CANT_MASTS (SINGLE_ELE_LIST (YARD_DATA_COLLECT_GPS BLOCKS_LIST '("DOUBLE_CANT_MAST" "TRIPLE_CANT_MAST" "SS2" "SS3") 1 3) 0))
 (SETQ MAST_UP (FILTER_LIST '("UP") MAST_TTC_DIR 1))
 (SETQ MAST_DN (FILTER_LIST '("DN") MAST_TTC_DIR 1))
  
 (SETQ ANCHOR_START  (BUILD_LIST (ENTITY_DFX (SINGLE_ELE_LIST ANCHOR_START 0)  10 -1) (LIST 0 1)))
 (SETQ ANCHOR_END  (BUILD_LIST (ENTITY_DFX (SINGLE_ELE_LIST ANCHOR_END 0)  10 -1) (LIST 0 1)))

  
  (IF (/= ANCHOR_START NIL) (SETQ ANCHOR_START_STRUCTURE_MAP_DATA (DATA_TO_STRUCTURE_MAP_SECTIONING ANCHOR_START MAST_TTC 1 1)) (SETQ ANCHOR_START NIL))
  (IF (/= ANCHOR_END NIL) (SETQ ANCHOR_END_STRUCTURE_MAP_DATA (DATA_TO_STRUCTURE_MAP_SECTIONING ANCHOR_END MAST_TTC 1 1)) (SETQ ANCHOR_END NIL))
  
  (IF (/= ACC_LIST NIL) (SETQ ACC_STRUCTURE_MAP_DATA (DATA_TO_STRUCTURE_MAP_SECTIONING ACC_LIST MAST_TTC 1 1)) (SETQ ACC_STRUCTURE_MAP_DATA NIL))



  
 (SETQ MAST_UP  (ADD_LISTS (BUILD_LIST (ENTITY_DFX (SINGLE_ELE_LIST MAST_UP 0)  10 -1) (LIST 0 1)) (N_ELE_LIST "UP" (LENGTH MAST_UP))))
 (SETQ MAST_DN  (ADD_LISTS (BUILD_LIST (ENTITY_DFX (SINGLE_ELE_LIST MAST_DN 0)  10 -1) (LIST 0 1)) (N_ELE_LIST "DN" (LENGTH MAST_DN))))

  (IF (/= BTB_ANCHOR_ENTITIES NIL) (SETQ BTB_ANCHOR_STRUCTURE_MAP_DATA_TOTAL (DATA_TO_STRUCTURE_MAP_SECTIONING BTB_ANCHOR_ENTITIES (APPEND MAST_UP MAST_DN) 1 1)) (SETQ BTB_ANCHOR_ENTITIES NIL))
  (SETQ BTB_ANCHOR_STRUCTURE_MAP_DATA_TOTAL (BUILD_LIST (SORT_ENTITIES_ALONG_CURVE1 TRACK_ENTITY_UPTRACK (ADD_LISTS BTB_ANCHOR_STRUCTURE_MAP_DATA_TOTAL (SINGLE_ELE_LIST (ENTITY_DFX (SINGLE_ELE_LIST BTB_ANCHOR_STRUCTURE_MAP_DATA_TOTAL 0)  10 -1) 1)) (LIST 1 STARTING_POINT) 1 1) (LIST 0 1 3)))

  
  (SETQ I 0 DATA_TO_PRINT NIL)
  ;(SETQ CURVE_DATA (GET_CURVE_DATA_RET))
  (SETQ MASTS_TO_BE_CONSIDERED (SINGLE_ELE_LIST MAST_TTC 0))
  
  (WHILE (< I (LENGTH MASTS_TO_BE_CONSIDERED))

  
    (SETQ LOC_DATA (NTH 0 (GET_CO-ORDINATES (LIST (NTH I MASTS_TO_BE_CONSIDERED)))))
    (SETQ TEST_ANCHOR NIL TEST_ACC NIL TEST_BTB NIL TEST_MULT NIL LOC_TYPE "NORMAL")
    ;(SETQ CURVE_DETAILS (CURVE_TEST ELE1_ELE2 CURVE_DATA))
    (IF (/= ANCHOR_START_STRUCTURE_MAP_DATA NIL) (SETQ TEST_ANCHOR_START (FILTER_LIST (LIST (NTH I MASTS_TO_BE_CONSIDERED)) ANCHOR_START_STRUCTURE_MAP_DATA 1)))
    (IF (/= ANCHOR_END_STRUCTURE_MAP_DATA NIL) (SETQ TEST_ANCHOR_END (FILTER_LIST (LIST (NTH I MASTS_TO_BE_CONSIDERED)) ANCHOR_END_STRUCTURE_MAP_DATA 1)))
    (IF (/= ACC_STRUCTURE_MAP_DATA NIL) (SETQ TEST_ACC (FILTER_LIST (LIST (NTH I MASTS_TO_BE_CONSIDERED)) ACC_STRUCTURE_MAP_DATA 1)))
    (IF (/= BTB_ANCHOR_STRUCTURE_MAP_DATA_TOTAL NIL) (SETQ TEST_BTB (FILTER_LIST (LIST (NTH I MASTS_TO_BE_CONSIDERED)) BTB_ANCHOR_STRUCTURE_MAP_DATA_TOTAL 1)))
    (IF (/= MULTIPLE_CANT_MASTS NIL) (IF (/= (VL-POSITION (NTH I MASTS_TO_BE_CONSIDERED) MULTIPLE_CANT_MASTS) NIL) (SETQ TEST_MULT 1)))
    
    (IF (/= TEST_ANCHOR_START NIL)
      (SETQ LOC_TYPE (STRCAT (NTH 0 (SINGLE_ELE_LIST (EXTRACT_ATTRIBUTES (NTH 0 (NTH 0 TEST_ANCHOR_START)) (LIST "ANCHOR_TYPE1" ) 1) 1)) "START"))
    )
    
    (IF (/= TEST_ANCHOR_END NIL)
      (SETQ LOC_TYPE (STRCAT (NTH 0 (SINGLE_ELE_LIST (EXTRACT_ATTRIBUTES (NTH 0 (NTH 0 TEST_ANCHOR_END)) (LIST "ANCHOR_TYPE1" ) 1) 1)) "END"))
    )
    
    (IF (/= TEST_ACC NIL)
      (SETQ LOC_TYPE "ACC")
    )
    (IF (/= TEST_BTB NIL)
      (SETQ LOC_TYPE (STRCAT (NTH 0 (SINGLE_ELE_LIST (EXTRACT_ATTRIBUTES (NTH 0 (NTH 0 TEST_BTB)) (LIST "ANCHOR_TYPE1" ) 1) 1)) "/" (NTH 0 (SINGLE_ELE_LIST (EXTRACT_ATTRIBUTES (NTH 0 (NTH 0 TEST_BTB)) (LIST "ANCHOR_TYPE2" ) 1) 1))))
    )
    (IF (/= TEST_MULT NIL)
      (SETQ LOC_TYPE "DOUBLE CANTILEVER LOCATION")
    )
    ;(IF (/= (NTH 0 CURVE_DETAILS) NIL) (SETQ IMPLANTATION "3.50"))
    (SETQ DATA_TO_PRINT (CONS (LIST (NTH 0 LOC_DATA) (NTH 1 LOC_DATA) (NTH 2 LOC_DATA) (NTH 3 LOC_DATA) (NTH 4 LOC_DATA) (NTH 5 LOC_DATA) (NTH 6 LOC_DATA) (NTH 7 LOC_DATA) LOC_TYPE) DATA_TO_PRINT))
    
    (SETQ I (+ I 1))

 )

  (SETQ DATA_TO_PRINT (REVERSE DATA_TO_PRINT))
  (PUTCELLSHEET "Sheet1" (COLUMN+N STARTING_CELL 0) (SINGLE_ELE_LIST DATA_TO_PRINT 0))
  (PUTCELLSHEET "Sheet1" (COLUMN+N STARTING_CELL 1) (SINGLE_ELE_LIST DATA_TO_PRINT 1))
  (PUTCELLSHEET "Sheet1" (COLUMN+N STARTING_CELL 2) (SINGLE_ELE_LIST DATA_TO_PRINT 2))
  (PUTCELLSHEET "Sheet1" (COLUMN+N STARTING_CELL 3) (SINGLE_ELE_LIST DATA_TO_PRINT 3))
  (PUTCELLSHEET "Sheet1" (COLUMN+N STARTING_CELL 4) (SINGLE_ELE_LIST DATA_TO_PRINT 4))
  (PUTCELLSHEET "Sheet1" (COLUMN+N STARTING_CELL 5) (SINGLE_ELE_LIST DATA_TO_PRINT 5))
  (PUTCELLSHEET "Sheet1" (COLUMN+N STARTING_CELL 6) (SINGLE_ELE_LIST DATA_TO_PRINT 6))
  (PUTCELLSHEET "Sheet1" (COLUMN+N STARTING_CELL 7) (SINGLE_ELE_LIST DATA_TO_PRINT 7))
  (PUTCELLSHEET "Sheet1" (COLUMN+N STARTING_CELL 8) (SINGLE_ELE_LIST DATA_TO_PRINT 8))
  
)

(DEFUN REMOVE_NIL (LIST1 / I FINAL_LIST)
  (SETQ I 0)
  (WHILE (< I (LENGTH LIST1))
    (IF (/= (NTH I LIST1) NIL) (SETQ FINAL_LIST (CONS (NTH I LIST1) FINAL_LIST)))
    (SETQ I (+ I 1))
  )
(REVERSE FINAL_LIST)
)


(DEFUN C:EXTRACT_OFFSETS ( / POLYLINE_ENTITY COPY_ENTITY POINT1 POINT2 START_CELL END_CELL SPANLIST)
    (COMMAND "UCS" "W")
    (SETQ OS_MODE (GETVAR "OSMODE"))
  (SETVAR "OSMODE" 0)
  (SETQ POLYLINE_ENTITY (CAR(ENTSEL "\n SELECT TRACK REFERENCE")))
  (SETQ COPY_ENTITY (CAR(ENTSEL "\n SELECT OBJECT FOR OFFSET")))
  (SETQ POINT1 (GETPOINT "\n PICK STARTING POINT ON CURVE"))
  (SETQ POINT2 (GETPOINT "\n PICK ANY POINT ON CURVE IN REQUIRED DIRECTION"))
  (SETQ START_CELL (GETSTRING "\n ENTER STARTING CELL IN EXCEL"))
  (SETQ END_CELL (GETSTRING "\n ENTER STARTING CELL IN EXCEL"))
  (OPENEXCEL (FINDFILE "SPANEXTRACT.XLSX") "Sheet1" T)
  (SETQ SPANLIST (getCellsrow/column "Sheet1" (STRCAT (COLUMN+N START_CELL 0) ":" (COLUMN+N END_CELL 0))))
  (SETQ COLOURLIST (getCellsrow/column "Sheet1" (STRCAT (COLUMN+N START_CELL 1) ":" (COLUMN+N END_CELL 1))))
  (OFFSETS POLYLINE_ENTITY COPY_ENTITY POINT1 POINT2 SPANLIST COLOURLIST)
    (SETVAR "OSMODE" OS_MODE)
  (COMMAND "UCS" "P")
)

(DEFUN OFFSETS (POLYLINE_ENTITY COPY_ENTITY POINT1 POINT2 SPAN_LIST COLOURLIST /  OS_MODE DIRECTION TEMP_DISTANCE I TEMP_ELE DIST DIRECTION NEXT_POINT TEMP_ELE )



  (SETQ DIRECTION (FIND_DIRECTION POLYLINE_ENTITY POINT1 POINT2))
  (SETQ TEMP_DISTANCE (VLAX-CURVE-GETDISTATPOINT POLYLINE_ENTITY POINT1))
  (SETQ I 0 TEMP_ELE NIL DIST 0)
  (WHILE (< I (LENGTH SPAN_LIST))
    (SETQ DIST (NTH I SPAN_LIST))
    (IF (/= DIST NIL)
    (PROGN
    (IF (= DIRECTION "POSITIVE")
      (SETQ TEMP_DISTANCE (- TEMP_DISTANCE DIST))
      (SETQ TEMP_DISTANCE (+ TEMP_DISTANCE DIST))
    )
    (SETQ NEXT_POINT (VLAX-CURVE-GETPOINTATDIST POLYLINE_ENTITY TEMP_DISTANCE))
    (SETQ TEMP_ELE (COPY_ORTHOGONAL POLYLINE_ENTITY COPY_ENTITY POINT1 NEXT_POINT TEMP_DISTANCE))
    (VLAX-PUT-PROPERTY (VLAX-ENAME->VLA-OBJECT (ENTLAST)) 'COLOR (NTH I COLOURLIST))
    (SETQ COPY_ENTITY (NTH 0 TEMP_ELE) POINT1 (NTH 1 TEMP_ELE))
    )
    )
    (SETQ I (+ I 1))
  )

)






(DEFUN SPAN_FROM_OFFSETS_SPECIAL (TRACK_CENTER INTERSECTION_POINT FLAG / I TEMP_SPAN FINAL_LIST)
  (SETQ I 0 TEMP_SPAN NIL FINAL_LIST NIL)
  (WHILE (< I (LENGTH INTERSECTION_POINT))
    (IF (/= I (- (LENGTH INTERSECTION_POINT) 1)) (SETQ TEMP_SPAN (RTOS (APPROXIMATE_SPAN (DISTANCE_ON_CURVE_GPS TRACK_CENTER (NTH FLAG (NTH I INTERSECTION_POINT)) (NTH FLAG (NTH (+ I 1) INTERSECTION_POINT))) 0.5) 2 2)) (SETQ TEMP_SPAN NIL))
    (SETQ COLOUR (CDR (ASSOC 62  (ENTGET (NTH FLAG (NTH I INSERTION_POINTS_SPAN))))))
    (SETQ FINAL_LIST (CONS (APPEND (NTH I INTERSECTION_POINT) (LIST TEMP_SPAN COLOUR)) FINAL_LIST))
    (SETQ I (+ I 1))
  )
  (REVERSE FINAL_LIST)
)





(DEFUN GET_DATA_TO_BE_FILLED2 (LOC_LIST / CANT_FLAG)
  (SETQ CANT_FLAG 0)
  (IF (/= LOC_LIST NIL)
    (PROGN
      (SETQ LOC_LIST (EXTRACT_ENTITY_INFO2 LOC_LIST))
      (SETQ LOC_LIST (FRAME_LIST2
		       (LIST '("SINGLE_CANT_MAST"
			       "DOUBLE_CANT_MAST"
			       "TRIPLE_CANT_MAST"
			      )
			     '("SUPER_MAST")
			     '("ANCHOR" "BTB_ANC")
		       )
		       LOC_LIST
		       1
		     )
      )
      (IF (/= (VL-POSITION
		"SINGLE_CANT_MAST"
		(SINGLE_ELE_LIST LOC_LIST 1)
	      )
	      NIL
	  )
	(SETQ CANT_FLAG 1)
      )
      (IF (/= (VL-POSITION
		"DOUBLE_CANT_MAST"
		(SINGLE_ELE_LIST LOC_LIST 1)
	      )
	      NIL
	  )
	(SETQ CANT_FLAG 2)
      )
      (IF (/= (VL-POSITION
		"TRIPLE_CANT_MAST"
		(SINGLE_ELE_LIST LOC_LIST 1)
	      )
	      NIL
	  )
	(SETQ CANT_FLAG 3)
      )
      (SETQ LOC_LIST (SINGLE_ELE_LIST LOC_LIST 0))
      (SETQ LOC_LIST (ASSEMBLE_DATA LOC_LIST))
    )
  )
  (LIST LOC_LIST CANT_FLAG)
)



(DEFUN ASSEMBLE_DATA (LIST1 / MAST_DATA SM_DATA ANCHOR_DATA FINAL_LIST)
  (SETQ	MAST_DATA NIL
	SM_DATA	NIL
	ANCHOR_DATA NIL
  )
  (SETQ MAST_DATA (MAST_DATA_EXTRACT (NTH 0 LIST1)))
  (IF (/= (NTH 1 LIST1) NIL)
    (SETQ SM_DATA (SM_DATA_EXTRACT (NTH 1 LIST1)))
  )
  (IF (/= (NTH 2 LIST1) NIL)
    (SETQ ANCHOR_DATA (ANCHOR_DATA_EXTRACT (NTH 2 LIST1)))
  )
  (IF (/= (NTH 3 LIST1) NIL)
    (SETQ PLATFORM_DATA (PLATFORM_DATA_EXTRACT (NTH 3 LIST1)))
  )
  (SETQ FINAL_LIST (APPEND MAST_DATA SM_DATA ANCHOR_DATA PLATFORM_DATA))
  (SETQ	FINAL_LIST
	 (FRAME_LIST
	   (LIST "KM_NO"	    "LOC_NO"
		 "CHAINAGE"	    "MAST_TYPE"
		 "TYPE_OF_LOCATION" "IMPLANTATION1"
		 "MAST_ORIENTATION" "BRACKET_ORIENTATION"
		 "RADIUS"	    "SUPER_ELEVATION"
		 "RADIUS_TYPE"	    "TRACK_TYPE"
		 "TS"		    "TC1"
		 "RL"		    "ACC"
		 "WIRE_SYSTEM"	    "WIRE_NATURE1"
		 "STAGGER1"	    "WIRE_NATURE2"
		 "STAGGER2"	    "WIRE_NATURE3"
		 "STAGGER3"	    "OBLIGATORY_WIRE_SEQUENCE"
		 "SPAN1"	    "SPAN2"
		 "SPAN3"	    "AEW"
		 "BEC"		    "APEC"
		 "SM"		    "SUPER_MAST_TYPE"
		 "CROSS_ARM_TYPE"   "SM_ORIENTATION"
		 "PL1"		    "PLATFORM_TYPE"
		 "ANCHOR_TYPE1"	    "ANCHOR_NATURE1"
		 "ANCHOR_TYPE2"	    "ANCHOR_NATURE2"
		 "ANCHOR_ORIENTATION"
		 "JUMPER"	    "ISOLATOR"
		 "SI"		    "PTFE"
		 "CI"		    "FOUNDATION_TYPE1"
		 "RD1"		    "ANCHOR_FOUNDATION1"
		 "ANCHOR_FOUNDATION2"
		)
	   FINAL_LIST
	   1
	 )
  )
  (MAP_ELEMENTS1
    (SINGLE_ELE_LIST FINAL_LIST 1)
    (LIST NIL)
    (LIST "")
  )
)





(DEFUN MAST_DATA_EXTRACT (ENTNAME	   /
			  ENTNAME	   ATTR_SET
			  LOC_INFO_SET	   FLIP_STATES
			  MAST_FLIP_STATES STAGGERS
			  SUB_LIST1	   SUB_LIST2
			  FINAL_SUB_LIST   BRACKET_ORIENTATION
			 )

  (SETQ ATTR_SET (SORT_FUN (GET_ATTRIBUTES1 ENTNAME) 2 0))
  (SETQ ATTR_SET1 (SORT_FUN (GET_ATTRIBUTES ENTNAME) 2 0))
  (SETQ LOC_INFO_SET (GET_LOC ATTR_SET))

;;;;;
  (SETQ	FLIP_STATES
	 (GET_FLIPSTATES
	   ENTNAME
	   (VLAX-GET-PROPERTY
	     (VLAX-ENAME->VLA-OBJECT ENTNAME)
	     "EFFECTIVENAME"
	   )
	 )
  )
  (SETQ MAST_FLIP_STATES (NTH 0 FLIP_STATES))
  (IF (= MAST_FLIP_STATES "UP")
    (SETQ MAST_FLIP_STATES (LIST "MAST_ORIENTATION" "UP"))
    (SETQ MAST_FLIP_STATES (LIST "MAST_ORIENTATION" "DN"))
  )
  (SETQ
    STAGGERS (BUILD_LIST
	       (FILTER_LIST
		 (LIST 1)
		 (FILTER_LIST
		   '("STAGGER"		"STAGGER1"
		     "STAGGER2"		"STAGGER3"
		     "NULL_STAGGER"	"NULL_STAGGER1"
		     "NULL_STAGGER2"
		    )
		   (MERGE_FLIPSTATES ATTR_SET1 (NTH 1 FLIP_STATES))
		   0
		 )
		 3
	       )
	       (LIST 0 1 4)
	     )
  )
  (SETQ STAGGERS (STAGGER_SIGNS (NTH 1 MAST_FLIP_STATES) STAGGERS))
;;;;;



  (SETQ	SUB_LIST1 (FRAME_LIST
		    (LIST "TYPE_OF_LOCATION"
			  "IMPLANTATION1"  "TRACK_TYPE"
			  "ACC"		   "RL"
			  "WIRE_SYSTEM"	   "WIRE_NATURE1"
			  "WIRE_NATURE2"   "WIRE_NATURE3"
			  "SPAN1"	   "SPAN2"
			  "SPAN3"	   "BEC"
			  "AEW"		   "APEC"
			  "PL1"		   "SUPER_ELEVATION"
			  "RADIUS"	   "RADIUS_TYPE"
			  "FOUNDATION_TYPE1"
			  "RD1"
			 )
		    ATTR_SET
		    1
		  )
  )


  (SETQ
    STL	(GET_DYNAMIC_PROPERTIES ENTNAME (LIST "STL1" "STL2" "STL3"))
  )
  (IF (/= (ASSOC "STL2" STL) NIL)
    (PROGN
      (IF (= (ASSOC "STL3" STL) NIL)
	(PROGN
	  (IF (< (CADR (ASSOC "STL1" STL)) (CADR (ASSOC "STL2" STL)))
	    (SETQ BRACKET_ORIENTATION "LEFT")
	    (SETQ BRACKET_ORIENTATION "RIGHT")
	  )
	)
	(PROGN
	  (IF (< (CADR (ASSOC "STL1" STL)) (CADR (ASSOC "STL3" STL)))
	    (SETQ BRACKET_ORIENTATION "LEFT")
	    (SETQ BRACKET_ORIENTATION "RIGHT")
	  )
	)
      )
    )
    (PROGN (SETQ BRACKET_ORIENTATION NIL))
  )

  (SETQ	SUB_LIST3
	 (LIST
	   (LIST
	     "TC1"
	     (NTH 0
		  (STRING_BREAK (NTH 1 (ASSOC "TC1" ATTR_SET)) "=")
	     )
	   )
	   (LIST "BRACKET_ORIENTATION" BRACKET_ORIENTATION)
	 )
  )

;;;;;;
  (IF (/= (ASSOC "TS" ATTR_SET) NIL)
    (PROGN
      (IF (/= (NTH 3 (ASSOC "TS" ATTR_SET)) 0)
	(PROGN (SETQ SUB_LIST2 (FRAME_LIST
				 (LIST "TS" "OBLIGATORY_WIRE_SEQUENCE")
				 ATTR_SET
				 1
			       )
	       )
	)
	(PROGN (SETQ SUB_LIST2 (LIST (LIST "TS" NIL)
				     (LIST "OBLIGATORY_WIRE_SEQUENCE" NIL)
			       )
		     ATTR_SET  1
	       )
	)
      )
    )
  )
;;;;;;

  (SETQ	FINAL_SUB_LIST
	 (APPEND LOC_INFO_SET
		 SUB_LIST1
		 SUB_LIST2
		 SUB_LIST3
		 (LIST MAST_FLIP_STATES)
		 STAGGERS
	 )
  )
  (SETQ	FINAL_SUB_LIST
	 (FRAME_LIST
	   (LIST "KM_NO"	   "LOC_NO"	     "CHAINAGE"
		 "MAST_TYPE"	   "TYPE_OF_LOCATION"
		 "IMPLANTATION1"   "MAST_ORIENTATION"
		 "BRACKET_ORIENTATION"		     "TRACK_TYPE"
		 "TS"		   "TC1"	     "RL"
		 "ACC"		   "WIRE_SYSTEM"     "WIRE_NATURE1"
		 "STAGGER1"	   "WIRE_NATURE2"    "STAGGER2"
		 "WIRE_NATURE3"	   "STAGGER3"
		 "OBLIGATORY_WIRE_SEQUENCE"	     "SPAN1"
		 "SPAN2"	   "SPAN3"	     "AEW"
		 "BEC"		   "APEC"	     "PL1"
		 "FOUNDATION_TYPE1"		     "SUPER_ELEVATION"
		 "RADIUS"	   "RADIUS_TYPE"     "RD1"
		)
	   FINAL_SUB_LIST
	   1
	 )
  )
					;(MAP_ELEMENTS1 FINAL_SUB_LIST (LIST "0") (LIST ""))
					;(PUTCELLSHEET "PROIN" "F8" (MAP_ELEMENTS1 (SINGLE_ELE_LIST FINAL_SUB_LIST 1) (LIST nil) (LIST "")))
					;(DUMP_O/P_FROM_EXCEL_TO_TABLES)
)



(DEFUN GET_FLIPSTATES (ENTNAME BLKNAME / DN_ORIENTATION_STRUCTURES UP_ORIENTATION_STRUCTURES STRUCTURES_WITH_STAGGERS TEMP_ELE TEMP_ELE1 LIST2 STF ANF SGM_X J )
  (SETQ STRUCTURES (LIST "SINGLE_CANT_MAST" "SINGLE_CANT_DA" "SINGLE_CANT_UPRIGHT"  "SS1" "BOX_TYPE" "SPS" "DOUBLE_CANT_MAST"  "DOUBLE_CANT_DA" "TRIPLE_CANT_MAST"  "TRIPLE_CANT_DA" "SS2" "SS3" "DOUBLE_CANT_UPRIGHT" "TRIPLE_CANT_UPRIGHT" "TTC" "SS4"))
  (SETQ STRUCTURES_WITH_STAGGERS (LIST "SINGLE_CANT_MAST" "SINGLE_CANT_DA" "SS1" "BOX_TYPE" "DOUBLE_CANT_MAST"  "DOUBLE_CANT_DA" "TRIPLE_CANT_MAST"  "TRIPLE_CANT_DA" "SS2" "SS3" "SINGLE_CANT_UPRIGHT" "DOUBLE_CANT_UPRIGHT" "TRIPLE_CANT_UPRIGHT"))
  (SETQ TEMP_ELE NIL TEMP_ELE1 NIL LIST2 NIL)
  ;(SETQ BLKNAME (VLAX-GET-PROPERTY (VLAX-ENAME->VLA-OBJECT ENTNAME) "EFFECTIVENAME"))
  (SETQ STF (ASSOC "STF1" (GET_DYNAMIC_PROPERTIES ENTNAME (LIST "STF1"))))
  (SETQ ANF (ASSOC "ANF1" (GET_DYNAMIC_PROPERTIES ENTNAME (LIST "ANF1"))))
  (IF (/= STF NIL) (SETQ STF (NTH 1 STF)))
  (IF (/= ANF NIL) (SETQ ANF (NTH 1 ANF)))
  (IF (/= STF NIL)
  (PROGN 
  (IF (/= (VL-POSITION BLKNAME STRUCTURES) NIL)
    (PROGN (IF (= STF 0) (SETQ TEMP_ELE1 "DN") (SETQ TEMP_ELE1 "UP")))
  )
  
  
  )
  )
  (IF (/= ANF NIL)
  (PROGN (IF (= BLKNAME "ANCHOR")
    (PROGN (IF (= ANF 0) (SETQ TEMP_ELE1 "START") (SETQ TEMP_ELE1 "END")))
  ))
  )
  (IF (/= (VL-POSITION BLKNAME STRUCTURES_WITH_STAGGERS) NIL)
  (PROGN (SETQ SGF (GET_DYNAMIC_PROPERTIES ENTNAME (LIST "SGF1" "SGF2" "SGF3")))
         (SETQ SGM_X (GET_DYNAMIC_PROPERTIES ENTNAME (LIST "SGM1 X" "SGM2 X" "SGM3 X")))
         (SETQ  J 0)
         (WHILE (< J (LENGTH SGF))
	   (SETQ TEMP_ELE (LIST (NTH 1 (ASSOC (STRCAT "SGF" (ITOA (+ J 1))) SGF)) (NTH 1 (ASSOC (STRCAT "SGM" (ITOA (+ J 1)) " " "X") SGM_X))))
	   (SETQ LIST2 (CONS TEMP_ELE LIST2))
	   (SETQ J (+ J 1))
	 ))
  )
  (IF (/=  LIST2 NIL) 
    (SETQ LIST2 (MAP_ELEMENTS (SINGLE_ELE_LIST (SORT_FUN LIST2 0 1) 0) (LIST 0 1) (LIST "DN" "UP")))
  )
  (LIST TEMP_ELE1 LIST2)
)





(DEFUN C:UPDATE_SUPERBLOCK_AND_EXTRADEPTH ( / TOTAL_LIST LIST1 ENT_LIST I BLOCK_LIST FILTERED_LIST TEMP_LIST LOC_DETAILS PER)
(SETQ TOTAL_LIST (GET_TOTAL_LOC_LIST_GPS))
(SETQ BLOCKS_LIST (FORM_SSSET (SSGET "W" WPT1 WPT2 (LIST (CONS 0 "INSERT")))))
(SETQ TRACK_ENTITY_UPTRACK (ENTSEL "\nSELECT TRACK ALIGNMENT FOR UP TRACK (DN LINE):"))
(SETQ REF_MAST_DN (CAR (ENTSEL "\nSELECT REFERENCE MAST DNLINE:")))
(SETQ REF_MAST_UP (CAR (ENTSEL "\nSELECT REFERENCE MAST UPLINE:")))
(SETQ ATTRIBUTE_TAG1 "DUMMY_VARIABLE2")

  
   (setq dcl_id (load_dialog "DISPLAY_INFO.dcl"))
   (new_dialog "DISPLAY_INFO" dcl_id)
  
   
(SETQ FILTERED_LIST (APPEND (SINGLE_ELE_LIST TOTAL_LIST 0) (SINGLE_ELE_LIST TOTAL_LIST 1)))
  (SETQ I 0)
  (SETQ PER (/ (* (+ I 1) 100) (LENGTH FILTERED_LIST)))
  (SETQ TEMP_LIST NIL)
  (SETQ LOC_DETAILS NIL)
  
  (WHILE (< I (LENGTH FILTERED_LIST))
    (SET_TILE "INFO" (STRCAT "UPDATING FOUNDATION" " " (ITOA (+ I 1)) " " "OF" " "  (ITOA (LENGTH FILTERED_LIST))))
    (SET_TILE "PERCENTAGE" (STRCAT (RTOS PER 2 2) "%" " " "COMPLETED"))
    (IF (/= (NTH I FILTERED_LIST) NIL)
    (PROGN
    
    (SETQ TEMP_LIST (GET_DATA_TO_BE_FILLED2 (NTH I FILTERED_LIST)))
    (PUTCELLSHEET "PROIN" "F8" (NTH 0 TEMP_LIST))
    (SETQ DFCC_CHAINAGE (NTH 0 (SINGLE_ELE_LIST (EXTRACT_ATTRIBUTES (NTH 0 (NTH I FILTERED_LIST)) (LIST "CHAINAGE2" ) 1) 1)))
    (SETQ CONT_CHAINAGE (NTH 0 (SINGLE_ELE_LIST (EXTRACT_ATTRIBUTES (NTH 0 (NTH I FILTERED_LIST)) (LIST "CHAINAGE1" ) 1) 1)))
    (SETQ KM (SUBSTR DFCC_CHAINAGE 1 (VL-STRING-POSITION (ASCII "/") DFCC_CHAINAGE)))
    (SETQ CHAINAGE (SUBSTR DFCC_CHAINAGE (+ (VL-STRING-POSITION (ASCII "/") DFCC_CHAINAGE) 2)))
    (SETQ CONT_KM (SUBSTR CONT_CHAINAGE 1 (VL-STRING-POSITION (ASCII "/") CONT_CHAINAGE)))
    (PUTCELLSHEET "PROIN" "F8" KM)
    (PUTCELLSHEET "PROIN" "F10" CHAINAGE)
    (PUTCELLSHEET "PROIN" "K8" CONT_KM)
    (SETQ LOC_DETAILS (PARAMETERS_EXTRACT "Implantation" "A9:A11" "B9:B11"))
    (SETQ LOC_DETAILS (SINGLE_ELE_LIST LOC_DETAILS 1))
    (MODIFY_ATTRIBUTES (NTH 0 (NTH I FILTERED_LIST)) (lIST "SUPER_BLOCK/EXTRA_DEPTH" "RADIUS/SUPER_ELEVATION" "DUMMY_VARIABLE2") LOC_DETAILS)
    ;(MODIFY_ATTRIBUTES (NTH 0 (NTH I FILTERED_LIST)) (lIST "RD1") (LIST (RTOS (NTH 1 LOC_DETAILS) 2 0)))
    
    (IF (= I (- (LENGTH FILTERED_LIST) 1)) (PROGN (SET_TILE "INFO" "FOUNDATIONS ARE UPDATED") (SET_TILE "PERCENTAGE" "CLICK OK TO VIEW RESULTS")))
    )
    )
    (SETQ I (+ I 1))
    (SETQ PER (/ (* (+ I 1) 100) (LENGTH FILTERED_LIST)))
    )
    (setq ddiag(start_dialog))
  (SETQ BLOCK_NAME_LIST (EXTRACT_ENTITY_INFO2 BLOCKS_LIST))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_UP (FILTER_LIST '("UP") MAST_TTC_DIR 1))
  (SETQ MAST_DN (FILTER_LIST '("DN") MAST_TTC_DIR 1))
  (SETQ TOTAL_LIST (SINGLE_ELE_LIST (APPEND MAST_UP MAST_DN) 0))
  (SETQ I 0)
  (WHILE (< I (LENGTH TOTAL_LIST))
      (CHANGE_VISIBILITY (NTH I TOTAL_LIST) (LIST "SUPER_BLOCK/EXTRA_DEPTH" "RADIUS/SUPER_ELEVATION" "DUMMY_VARIABLE2") (LIST "1" "1" "1"))
      (SETQ  I (+ I 1))
  )
  
  ;(SETQ MAST_UP (SORT_ENTITIES_ALONG_CURVE1 (VLAX-ENAME->VLA-OBJECT (NTH 0 TRACK_ENTITY_UPTRACK)) MAST_UP (LIST 1 STARTING_POINT) 0 1))
  ;(SETQ MAST_DN (SORT_ENTITIES_ALONG_CURVE1 (VLAX-ENAME->VLA-OBJECT (NTH 0 TRACK_ENTITY_UPTRACK)) MAST_DN (LIST 1 STARTING_POINT) 0 1))

  (MATCH_POSITION1 REF_MAST_UP (SINGLE_ELE_LIST MAST_UP 0) ATTRIBUTE_TAG1)
  (MATCH_POSITION1 REF_MAST_DN (SINGLE_ELE_LIST MAST_DN 0) ATTRIBUTE_TAG1)
    
)





(DEFUN C:UPDATE_FOUNDATION_EMP4 ( / TOTAL_LIST LIST1 ENT_LIST I BLOCK_LIST FILTERED_LIST TEMP_LIST LOC_DETAILS PER)
(SETQ TOTAL_LIST (GET_TOTAL_LOC_LIST_GPS))
(SETQ BLOCKS_LIST (FORM_SSSET (SSGET "W" WPT1 WPT2 (LIST (CONS 0 "INSERT")))))
(SETQ TRACK_ENTITY_UPTRACK (ENTSEL "\nSELECT TRACK ALIGNMENT FOR UP TRACK (DN LINE):"))
;(SETQ ATTRIBUTE_TAG1 "FOUNDATION_TYPE1")
;(SETQ ATTRIBUTE_TAG2 "MAST_NUMBER_LINK1")
;(SETQ ATTRIBUTE_TAG3 "IR_CHAINAGE1")
  
  ;(SETQ REF_MAST_DN (CAR (ENTSEL "\nSELECT REFERENCE MAST DNLINE:")))
  ;(SETQ REF_MAST_UP (CAR (ENTSEL "\nSELECT REFERENCE MAST UPLINE:")))
  
   (setq dcl_id (load_dialog "DISPLAY_INFO.dcl"))
   (new_dialog "DISPLAY_INFO" dcl_id)
  
   
(SETQ FILTERED_LIST (APPEND (SINGLE_ELE_LIST TOTAL_LIST 0) (SINGLE_ELE_LIST TOTAL_LIST 1)))
  (SETQ I 0)
  (SETQ PER (/ (* (+ I 1) 100) (LENGTH FILTERED_LIST)))
  (SETQ TEMP_LIST NIL)
  (SETQ LOC_DETAILS NIL)
  
  (WHILE (< I (LENGTH FILTERED_LIST))
    (SET_TILE "INFO" (STRCAT "UPDATING FOUNDATION" " " (ITOA (+ I 1)) " " "OF" " "  (ITOA (LENGTH FILTERED_LIST))))
    (SET_TILE "PERCENTAGE" (STRCAT (RTOS PER 2 2) "%" " " "COMPLETED"))
    (IF (/= (NTH I FILTERED_LIST) NIL)
    (PROGN
    (SETQ TEMP_LIST (GET_DATA_TO_BE_FILLED2 (NTH I FILTERED_LIST)))
    (PUTCELLSHEET "PROIN" "F8" (NTH 0 TEMP_LIST))
    (SETQ DFCC_CHAINAGE (NTH 0 (SINGLE_ELE_LIST (EXTRACT_ATTRIBUTES (NTH 0 (NTH I FILTERED_LIST)) (LIST "CHAINAGE1" ) 1) 1)))
    
    (SETQ KM (SUBSTR DFCC_CHAINAGE 1 (VL-STRING-POSITION (ASCII "/") DFCC_CHAINAGE)))
    (SETQ CHAINAGE (SUBSTR DFCC_CHAINAGE (+ (VL-STRING-POSITION (ASCII "/") DFCC_CHAINAGE) 2)))
    
    (PUTCELLSHEET "PROIN" "F8" KM)
    (PUTCELLSHEET "PROIN" "F10" CHAINAGE)
    
    (SETQ LOC_DETAILS (PARAMETERS_EXTRACT "Implantation" "A17:A18" "B17:B18"))
    (SETQ LOC_DETAILS (SINGLE_ELE_LIST LOC_DETAILS 1))
    (MODIFY_ATTRIBUTES (NTH 0 (NTH I FILTERED_LIST)) (lIST "FOUNDATION_TYPE1" "RD1") LOC_DETAILS)
    (IF (= I (- (LENGTH FILTERED_LIST) 1)) (PROGN (SET_TILE "INFO" "FOUNDATIONS ARE UPDATED") (SET_TILE "PERCENTAGE" "CLICK OK TO VIEW RESULTS")))
    )
    )
    (SETQ I (+ I 1))
    (SETQ PER (/ (* (+ I 1) 100) (LENGTH FILTERED_LIST)))
    )
    (setq ddiag(start_dialog))
  (SETQ BLOCK_NAME_LIST (EXTRACT_ENTITY_INFO2 BLOCKS_LIST))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_UP (FILTER_LIST '("UP") MAST_TTC_DIR 1))
  (SETQ MAST_DN (FILTER_LIST '("DN") MAST_TTC_DIR 1))
  (SETQ TOTAL_LIST (SINGLE_ELE_LIST (APPEND MAST_UP MAST_DN) 0))
  ;(SETQ I 0)
  ;(WHILE (< I (LENGTH TOTAL_LIST))
      ;(CHANGE_VISIBILITY (NTH I TOTAL_LIST) (LIST ATTRIBUTE_TAG1) (LIST "1"))
      ;(CHANGE_VISIBILITY (NTH I TOTAL_LIST) (LIST ATTRIBUTE_TAG2) (LIST "1"))
      ;(CHANGE_VISIBILITY (NTH I TOTAL_LIST) (LIST ATTRIBUTE_TAG3) (LIST "1"))
      ;(SETQ  I (+ I 1))
  ;)
  
  ;(SETQ MAST_UP (SORT_ENTITIES_ALONG_CURVE1 (VLAX-ENAME->VLA-OBJECT (NTH 0 TRACK_ENTITY_UPTRACK)) MAST_UP (LIST 1 STARTING_POINT) 0 1))
  ;(SETQ MAST_DN (SORT_ENTITIES_ALONG_CURVE1 (VLAX-ENAME->VLA-OBJECT (NTH 0 TRACK_ENTITY_UPTRACK)) MAST_DN (LIST 1 STARTING_POINT) 0 1))

  ;(MATCH_POSITION1 REF_MAST_UP (SINGLE_ELE_LIST MAST_UP 0) ATTRIBUTE_TAG1)
  ;(MATCH_POSITION1 REF_MAST_DN (SINGLE_ELE_LIST MAST_DN 0) ATTRIBUTE_TAG1)
  ;(MATCH_POSITION1 REF_MAST_UP (SINGLE_ELE_LIST MAST_UP 0) ATTRIBUTE_TAG2)
  ;(MATCH_POSITION1 REF_MAST_DN (SINGLE_ELE_LIST MAST_DN 0) ATTRIBUTE_TAG2)
  ;(MATCH_POSITION1 REF_MAST_UP (SINGLE_ELE_LIST MAST_UP 0) ATTRIBUTE_TAG3)
  ;(MATCH_POSITION1 REF_MAST_DN (SINGLE_ELE_LIST MAST_DN 0) ATTRIBUTE_TAG3)
  
)



(DEFUN C:UPDATE_CORDINATES ( / )
(SETQ WPT1 (GETPOINT "\nPICK START OF LOP"))
(SETQ WPT2 (GETPOINT "\nPICK END OF LOP"))
(SETQ BLOCKS_LIST (FORM_SSSET (SSGET "W" WPT1 WPT2 (LIST (CONS 0 "INSERT")))))
(SETQ MAST_UP (FILTER_LIST '("UP") MAST_TTC_DIR 1))
(SETQ MAST_DN (FILTER_LIST '("DN") MAST_TTC_DIR 1))
(SETQ TRACK_ENTITY_DN (ENTSEL "\nSELECT TRACK ALIGNMENT FOR UP TRACK (DN LINE):"))
(SETQ TRACK_ENTITY_UP (ENTSEL "\nSELECT TRACK ALIGNMENT FOR DN TRACK (UP LINE):"))
(SETQ REF_MAST_DN (CAR (ENTSEL "\nSELECT REFERENCE MAST DNLINE:")))
(SETQ REF_MAST_UP (CAR (ENTSEL "\nSELECT REFERENCE MAST UPLINE:")))
(SETQ BLOCK_NAME_LIST (EXTRACT_ENTITY_INFO2 BLOCKS_LIST))
(SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))

(SETQ I 0)
(WHILE (< I (LENGTH MAST_TTC_DIR))
(IF (= (NTH 1 (NTH I MAST_TTC_DIR)) "DN")
(SETQ TEMP_ELE (VLAX-CURVE-GETCLOSESTPOINTTO (VLAX-ENAME->VLA-OBJECT (NTH 0 TRACK_ENTITY_DN)) (CDR (ASSOC 10 (ENTGET (NTH 0 (NTH I MAST_TTC_DIR))))) T))
(SETQ TEMP_ELE (VLAX-CURVE-GETCLOSESTPOINTTO (VLAX-ENAME->VLA-OBJECT (NTH 0 TRACK_ENTITY_UP)) (CDR (ASSOC 10 (ENTGET (NTH 0 (NTH I MAST_TTC_DIR))))) T))
)

(MODIFY_ATTRIBUTES (NTH 0 (NTH I MAST_TTC_DIR)) (lIST "DUMMY_VARIABLE1") (LIST (STRCAT "(" (RTOS (NTH 0 TEMP_ELE) 2 2) " , " (RTOS (NTH 1 TEMP_ELE) 2 2) ")")))
(SETQ I (+ I 1))
)
(SETQ ATTRIBUTE_TAG1 "DUMMY_VARIABLE1")
(MATCH_POSITION1 REF_MAST_UP (SINGLE_ELE_LIST MAST_UP 0) ATTRIBUTE_TAG1)
(MATCH_POSITION1 REF_MAST_DN (SINGLE_ELE_LIST MAST_DN 0) ATTRIBUTE_TAG1)
)



(DEFUN C:PRINT_TRACKCENTER_CORDINATES ( / )
(SETQ WPT1 (GETPOINT "\nPICK START OF LOP"))
(SETQ WPT2 (GETPOINT "\nPICK END OF LOP"))
(SETQ BLOCKS_LIST (FORM_SSSET (SSGET "W" WPT1 WPT2 (LIST (CONS 0 "INSERT")))))
(SETQ STARTING_CELL (GETSTRING  "\nENTER STARTING CELL"))
(SETQ TRACK_ENTITY_DN (ENTSEL "\nSELECT TRACK ALIGNMENT FOR UP TRACK (DN LINE):"))
(SETQ TRACK_ENTITY_UP (ENTSEL "\nSELECT TRACK ALIGNMENT FOR DN TRACK (UP LINE):"))

(SETQ BLOCK_NAME_LIST (EXTRACT_ENTITY_INFO2 BLOCKS_LIST))
(SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
(SETQ TEMP_ELE NIL FINAL_LIST NIL TEMP_NO NIL)
(SETQ I 0)
(WHILE (< I (LENGTH MAST_TTC_DIR))
(IF (= (NTH 1 (NTH I MAST_TTC_DIR)) "DN")
(SETQ TEMP_ELE (VLAX-CURVE-GETCLOSESTPOINTTO (VLAX-ENAME->VLA-OBJECT (NTH 0 TRACK_ENTITY_DN)) (CDR (ASSOC 10 (ENTGET (NTH 0 (NTH I MAST_TTC_DIR))))) T))
(SETQ TEMP_ELE (VLAX-CURVE-GETCLOSESTPOINTTO (VLAX-ENAME->VLA-OBJECT (NTH 0 TRACK_ENTITY_UP)) (CDR (ASSOC 10 (ENTGET (NTH 0 (NTH I MAST_TTC_DIR))))) T))
)
(SETQ TEMP_NO (NTH 0 (SINGLE_ELE_LIST (EXTRACT_ATTRIBUTES (NTH 0 (NTH I MAST_TTC_DIR)) (LIST "MAST_NUMBER1" ) 1) 1)))
(SETQ FINAL_LIST (CONS  (LIST TEMP_NO (RTOS (NTH 0 TEMP_ELE) 2 2) (RTOS (NTH 1 TEMP_ELE) 2 2) ) FINAL_LIST))
(SETQ I (+ I 1))
)
    (PUTCELLSHEET "Sheet1" (COLUMN+N STARTING_CELL 0) (SINGLE_ELE_LIST (REVERSE FINAL_LIST) 0))
    (PUTCELLSHEET "Sheet1" (COLUMN+N STARTING_CELL 1) (SINGLE_ELE_LIST (REVERSE FINAL_LIST) 1))
    (PUTCELLSHEET "Sheet1" (COLUMN+N STARTING_CELL 2) (SINGLE_ELE_LIST (REVERSE FINAL_LIST) 2))
)






(DEFUN C:PRINT_LOC_DETAILS ( / )
   (SETQ BLOCKS_LIST (FORM_SSSET (SSGET "X" (LIST (CONS 0 "INSERT")))))
   (SETQ TRACK_ENTITY_DN (ENTSEL "\nSELECT TRACK ALIGNMENT FOR UP TRACK (DN LINE):"))
   (SETQ TRACK_ENTITY_UP (ENTSEL "\nSELECT TRACK ALIGNMENT FOR DN TRACK (UP LINE):"))
   (SETQ BLOCK_NAME_LIST (EXTRACT_ENTITY_INFO2 BLOCKS_LIST))
   (SETQ ENT_LIST (SINGLE_ELE_LIST (FILTER_LIST (LIST "SINGLE_CANT_MAST" "DOUBLE_CANT_MAST" "TRIPLE_CANT_MAST" "TTC" "SS0" "SS1" "SS2" "SS3" "SS4") BLOCK_NAME_LIST 1) 0))
   (SETQ STARTING_MAST (CAR(ENTSEL "N/ SELECT STARTING MAST")))
   (SETQ TRACK_CENTER (CAR(ENTSEL "N/ SELECT TRACK CENTER")))
   (SETQ STARTING_CELL (GETSTRING "N/ ENTER STARTING CELL"))
   ;(SETQ ENT_LIST (FORM_SSSET SSSET))
   (SETQ ENT_LIST (EXTRACT_ENTITY_INFO ENT_LIST 1 3))
   (SETQ ENT_LIST (SORT_MASTS ENT_LIST STARTING_MAST))
    (SETQ DETAILS_TO_PRINT (GET_CO-ORDINATES2 (SINGLE_ELE_LIST ENT_LIST 0) TRACK_ENTITY_DN TRACK_ENTITY_UP))
    (PUTCELLSHEET "Sheet1" (COLUMN+N STARTING_CELL 0) (SINGLE_ELE_LIST DETAILS_TO_PRINT 0))
    (PUTCELLSHEET "Sheet1" (COLUMN+N STARTING_CELL 1) (SINGLE_ELE_LIST DETAILS_TO_PRINT 1))
    (PUTCELLSHEET "Sheet1" (COLUMN+N STARTING_CELL 2) (SINGLE_ELE_LIST DETAILS_TO_PRINT 2))
    (PUTCELLSHEET "Sheet1" (COLUMN+N STARTING_CELL 3) (SINGLE_ELE_LIST DETAILS_TO_PRINT 3))
    (PUTCELLSHEET "Sheet1" (COLUMN+N STARTING_CELL 4) (SINGLE_ELE_LIST DETAILS_TO_PRINT 4))
    (PUTCELLSHEET "Sheet1" (COLUMN+N STARTING_CELL 5) (SINGLE_ELE_LIST DETAILS_TO_PRINT 5))
    (PUTCELLSHEET "Sheet1" (COLUMN+N STARTING_CELL 6) (SINGLE_ELE_LIST DETAILS_TO_PRINT 6))
    (PUTCELLSHEET "Sheet1" (COLUMN+N STARTING_CELL 7) (SINGLE_ELE_LIST DETAILS_TO_PRINT 7))
    (PUTCELLSHEET "Sheet1" (COLUMN+N STARTING_CELL 8) (SINGLE_ELE_LIST DETAILS_TO_PRINT 8))
    (PUTCELLSHEET "Sheet1" (COLUMN+N STARTING_CELL 9) (SINGLE_ELE_LIST DETAILS_TO_PRINT 9))
    (PUTCELLSHEET "Sheet1" (COLUMN+N STARTING_CELL 10) (SINGLE_ELE_LIST DETAILS_TO_PRINT 10))
    (PUTCELLSHEET "Sheet1" (COLUMN+N STARTING_CELL 11) (SINGLE_ELE_LIST DETAILS_TO_PRINT 11))
    (PUTCELLSHEET "Sheet1" (COLUMN+N STARTING_CELL 12) (SINGLE_ELE_LIST DETAILS_TO_PRINT 12))
    (PUTCELLSHEET "Sheet1" (COLUMN+N STARTING_CELL 13) (SINGLE_ELE_LIST DETAILS_TO_PRINT 13))
)



(DEFUN C:LOAD_EXCEL_GPS ( / )
  (OPENEXCEL (FINDFILE "SPANEXTRACT.XLSX") "Sheet1" T)
)

(DEFUN C:LOAD_OBSTRUCTION_FILE ( / )
  (OPENEXCEL (FINDFILE (GETFILED "SELECT OBSTRUCTION FILE" "" "" 8)) "Sheet1" T)
)

(DEFUN GET_CO-ORDINATES2 ( ENT_LIST TRACK_ENTITY_DN TRACK_ENTITY_UP / ENT_LIST I TEMP_CHAINAGE1 TEMP_CHAINAGE2 TEMP_EFFNAME TEMP_SPAN FINAL_LIST)
  (SETQ I 0 TEMP_CHAINAGE NIL TEMP_EFFNAME NIL TEMP_SPAN NIL FINAL_LIST NIL)
  (WHILE (< I (LENGTH ENT_LIST))
    (SETQ TEMP_NUMBER (NTH 0 (SINGLE_ELE_LIST (EXTRACT_ATTRIBUTES (NTH I ENT_LIST) (LIST "MAST_NUMBER1" ) 1) 1)))
    (SETQ TEMP_CHAINAGE1 (NTH 0 (SINGLE_ELE_LIST (EXTRACT_ATTRIBUTES (NTH I ENT_LIST) (LIST "CHAINAGE1" ) 1) 1)))
    (SETQ TEMP_CHAINAGE2 (NTH 0 (SINGLE_ELE_LIST (EXTRACT_ATTRIBUTES (NTH I ENT_LIST) (LIST "CHAINAGE2" ) 1) 1)))
    (SETQ TEMP_MAST (NTH 0 (SINGLE_ELE_LIST (EXTRACT_ATTRIBUTES (NTH I ENT_LIST) (LIST "MAST_TYPE1" ) 1) 1)))
    (SETQ TEMP_IMP (NTH 0 (SINGLE_ELE_LIST (EXTRACT_ATTRIBUTES (NTH I ENT_LIST) (LIST "IMPLANTATION1" ) 1) 1)))
    (SETQ TEMP_EFFNAME (VLAX-GET-PROPERTY (VLAX-ENAME->VLA-OBJECT (NTH I ENT_LIST)) 'EFFECTIVENAME))
    (SETQ TEMP_SPAN (NTH 0 (SINGLE_ELE_LIST (EXTRACT_ATTRIBUTES (NTH I ENT_LIST) (LIST "SPAN1" ) 1) 1)))
    (SETQ TEMP_HRL (NTH 0 (SINGLE_ELE_LIST (EXTRACT_ATTRIBUTES (NTH I ENT_LIST) (LIST "DUMMY_VARIABLE2" ) 1) 1)))
    
    (SETQ FLIP (NTH 1 (NTH 0 (GET_DYNAMIC_PROPERTIES (NTH I ENT_LIST) '("STF1")))))
    
    (SETQ ROTATION (VLAX-GET-PROPERTY (VLAX-ENAME->VLA-OBJECT (NTH I ENT_LIST)) 'ROTATION))
    (SETQ TEMP_CO-ORDINATES (CDR (ASSOC 10 (ENTGET (NTH I ENT_LIST)))))
    (IF (= FLIP 0)
     (SETQ TEMP_CO-ORDINATES (MAPCAR 'RTOS (POLAR TEMP_CO-ORDINATES (+ (* 1 (/ PI 2)) ROTATION) (+ (- (ATOF TEMP_IMP) 3.00) 0.2))) TEMP_LINE "Dn Line")
     (SETQ TEMP_CO-ORDINATES (MAPCAR 'RTOS (POLAR TEMP_CO-ORDINATES (+ (* 3 (/ PI 2)) ROTATION) (+ (- (ATOF TEMP_IMP) 3.00) 0.2))) TEMP_LINE "Up Line")
    )

    (IF (= FLIP 0)
    (SETQ TEMP_CO-ORDINATES1 (MAPCAR 'RTOS (VLAX-CURVE-GETCLOSESTPOINTTO (VLAX-ENAME->VLA-OBJECT (NTH 0 TRACK_ENTITY_DN)) (CDR (ASSOC 10 (ENTGET (NTH I ENT_LIST)))) T)))
    (SETQ TEMP_CO-ORDINATES1 (MAPCAR 'RTOS (VLAX-CURVE-GETCLOSESTPOINTTO (VLAX-ENAME->VLA-OBJECT (NTH 0 TRACK_ENTITY_UP)) (CDR (ASSOC 10 (ENTGET (NTH I ENT_LIST)))) T)))
    )
    
    (SETQ FINAL_LIST (CONS (APPEND (LIST TEMP_NUMBER TEMP_CHAINAGE1 TEMP_CHAINAGE2 TEMP_MAST TEMP_IMP TEMP_SPAN TEMP_LINE TEMP_HRL) TEMP_CO-ORDINATES TEMP_CO-ORDINATES1) FINAL_LIST))
    (SETQ I (+ I 1))
  )
  (REVERSE FINAL_LIST)
  
)




(DEFUN C:UPDATE_CYLINDRICAL_FOUNDATION_DETAILS( / TOTAL_LIST LIST1 ENT_LIST I BLOCK_LIST FILTERED_LIST TEMP_LIST LOC_DETAILS PER)
(SETQ TOTAL_LIST (GET_TOTAL_LOC_LIST_GPS))
(SETQ BLOCKS_LIST (FORM_SSSET (SSGET "W" WPT1 WPT2 (LIST (CONS 0 "INSERT")))))
(SETQ TRACK_ENTITY_UPTRACK (ENTSEL "\nSELECT TRACK ALIGNMENT FOR UP TRACK (DN LINE):"))
(SETQ REF_MAST_DN (CAR (ENTSEL "\nSELECT REFERENCE MAST DNLINE:")))
(SETQ REF_MAST_UP (CAR (ENTSEL "\nSELECT REFERENCE MAST UPLINE:")))
(SETQ ATTRIBUTE_TAG_LIST (LIST "FOUNDATION_TYPE1" "RD1" "STEP_DISTANCE/EMBEDDED_LENGTH" "SUPER_BLOCK/EXTRA_DEPTH" "RADIUS/SUPER_ELEVATION" "DUMMY_VARIABLE2" "ANCHOR_BLOCK/ANCHOR_STEP/ANCHOR_SETTING_DISTANCE"))

  
   (setq dcl_id (load_dialog "DISPLAY_INFO.dcl"))
   (new_dialog "DISPLAY_INFO" dcl_id)
  
   
(SETQ FILTERED_LIST (APPEND (SINGLE_ELE_LIST TOTAL_LIST 0) (SINGLE_ELE_LIST TOTAL_LIST 1)))
  (SETQ I 0)
  (SETQ PER (/ (* (+ I 1) 100) (LENGTH FILTERED_LIST)))
  (SETQ TEMP_LIST NIL)
  (SETQ LOC_DETAILS NIL)
  
  (WHILE (< I (LENGTH FILTERED_LIST))
    (SET_TILE "INFO" (STRCAT "UPDATING FOUNDATION" " " (ITOA (+ I 1)) " " "OF" " "  (ITOA (LENGTH FILTERED_LIST))))
    (SET_TILE "PERCENTAGE" (STRCAT (RTOS PER 2 2) "%" " " "COMPLETED"))
    (IF (/= (NTH I FILTERED_LIST) NIL)
    (PROGN
    
    (SETQ TEMP_LIST (GET_DATA_TO_BE_FILLED2 (NTH I FILTERED_LIST)))
    (PUTCELLSHEET "PROIN" "F8" (NTH 0 TEMP_LIST))
    (SETQ DFCC_CHAINAGE (NTH 0 (SINGLE_ELE_LIST (EXTRACT_ATTRIBUTES (NTH 0 (NTH I FILTERED_LIST)) (LIST "CHAINAGE2" ) 1) 1)))
    (SETQ CONT_CHAINAGE (NTH 0 (SINGLE_ELE_LIST (EXTRACT_ATTRIBUTES (NTH 0 (NTH I FILTERED_LIST)) (LIST "CHAINAGE1" ) 1) 1)))
    (SETQ KM (SUBSTR DFCC_CHAINAGE 1 (VL-STRING-POSITION (ASCII "/") DFCC_CHAINAGE)))
    (SETQ CHAINAGE (SUBSTR DFCC_CHAINAGE (+ (VL-STRING-POSITION (ASCII "/") DFCC_CHAINAGE) 2)))
    (SETQ CONT_KM (SUBSTR CONT_CHAINAGE 1 (VL-STRING-POSITION (ASCII "/") CONT_CHAINAGE)))
    (PUTCELLSHEET "PROIN" "F8" KM)
    (PUTCELLSHEET "PROIN" "F10" CHAINAGE)
    (PUTCELLSHEET "PROIN" "K8" CONT_KM)
    (SETQ LOC_DETAILS (PARAMETERS_EXTRACT "Implantation" "A25:A31" "B25:B31"))
    (SETQ LOC_DETAILS (SINGLE_ELE_LIST LOC_DETAILS 1))   
    (MODIFY_ATTRIBUTES (NTH 0 (NTH I FILTERED_LIST)) (lIST "FOUNDATION_TYPE1" "RD1" "STEP_DISTANCE/EMBEDDED_LENGTH" "SUPER_BLOCK/EXTRA_DEPTH" "RADIUS/SUPER_ELEVATION" "DUMMY_VARIABLE2" "ANCHOR_BLOCK/ANCHOR_STEP/ANCHOR_SETTING_DISTANCE") LOC_DETAILS)
    ;(MODIFY_ATTRIBUTES (NTH 0 (NTH I FILTERED_LIST)) (lIST "RD1") (LIST (RTOS (NTH 1 LOC_DETAILS) 2 0)))
    
    (IF (= I (- (LENGTH FILTERED_LIST) 1)) (PROGN (SET_TILE "INFO" "FOUNDATIONS ARE UPDATED") (SET_TILE "PERCENTAGE" "CLICK OK TO VIEW RESULTS")))
    )
    )
    (SETQ I (+ I 1))
    (SETQ PER (/ (* (+ I 1) 100) (LENGTH FILTERED_LIST)))
    )
  (setq ddiag(start_dialog))
  (SETQ BLOCK_NAME_LIST (EXTRACT_ENTITY_INFO2 BLOCKS_LIST))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_UP (FILTER_LIST '("UP") MAST_TTC_DIR 1))
  (SETQ MAST_DN (FILTER_LIST '("DN") MAST_TTC_DIR 1))
  (SETQ TOTAL_LIST (SINGLE_ELE_LIST (APPEND MAST_UP MAST_DN) 0))
  (SETQ I 0)
  (WHILE (< I (LENGTH TOTAL_LIST))
      (CHANGE_VISIBILITY (NTH I TOTAL_LIST) (LIST "FOUNDATION_TYPE1" "RD1" "STEP_DISTANCE/EMBEDDED_LENGTH" "SUPER_BLOCK/EXTRA_DEPTH" "RADIUS/SUPER_ELEVATION" "DUMMY_VARIABLE2" "ANCHOR_BLOCK/ANCHOR_STEP/ANCHOR_SETTING_DISTANCE") (LIST "1" "1" "1" "1" "1" "1" "1"))
      (SETQ  I (+ I 1))
  )
  
  ;(SETQ MAST_UP (SORT_ENTITIES_ALONG_CURVE1 (VLAX-ENAME->VLA-OBJECT (NTH 0 TRACK_ENTITY_UPTRACK)) MAST_UP (LIST 1 STARTING_POINT) 0 1))
  ;(SETQ MAST_DN (SORT_ENTITIES_ALONG_CURVE1 (VLAX-ENAME->VLA-OBJECT (NTH 0 TRACK_ENTITY_UPTRACK)) MAST_DN (LIST 1 STARTING_POINT) 0 1))

  (SETQ I 0)
  (WHILE (< I (LENGTH ATTRIBUTE_TAG_LIST))
      (MATCH_POSITION1 REF_MAST_UP (SINGLE_ELE_LIST MAST_UP 0) (NTH I ATTRIBUTE_TAG_LIST))
      (MATCH_POSITION1 REF_MAST_DN (SINGLE_ELE_LIST MAST_DN 0) (NTH I ATTRIBUTE_TAG_LIST))
      (SETQ  I (+ I 1))
  )
     
)







(DEFUN C:UPDATE_IMPLANTATION1 ( / TOTAL_LIST LIST1 ENT_LIST I BLOCK_LIST FILTERED_LIST TEMP_LIST LOC_DETAILS PER)
(SETQ TOTAL_LIST (GET_TOTAL_LOC_LIST_GPS))
   (setq dcl_id (load_dialog "DISPLAY_INFO.dcl"))
   (new_dialog "DISPLAY_INFO" dcl_id)
  
   
(SETQ FILTERED_LIST (APPEND (SINGLE_ELE_LIST TOTAL_LIST 0) (SINGLE_ELE_LIST TOTAL_LIST 1)))
  (SETQ I 0)
  (SETQ PER (/ (* (+ I 1) 100) (LENGTH FILTERED_LIST)))
  (SETQ TEMP_LIST NIL)
  (SETQ LOC_DETAILS NIL)
  
  (WHILE (< I (LENGTH FILTERED_LIST))
    (SET_TILE "INFO" (STRCAT "UPDATING FOUNDATION" " " (ITOA (+ I 1)) " " "OF" " "  (ITOA (LENGTH FILTERED_LIST))))
    (SET_TILE "PERCENTAGE" (STRCAT (RTOS PER 2 2) "%" " " "COMPLETED"))
    (IF (/= (NTH I FILTERED_LIST) NIL)
    (PROGN
    (SETQ TEMP_LIST (GET_DATA_TO_BE_FILLED2 (NTH I FILTERED_LIST)))
    (PUTCELLSHEET "PROIN" "F8" (NTH 0 TEMP_LIST))
    ;NEWLYADDED
    (SETQ DFCC_CHAINAGE (NTH 0 (SINGLE_ELE_LIST (EXTRACT_ATTRIBUTES (NTH 0 (NTH I FILTERED_LIST)) (LIST "CHAINAGE2" ) 1) 1)))
    (SETQ KM (SUBSTR DFCC_CHAINAGE 1 (VL-STRING-POSITION (ASCII "/") DFCC_CHAINAGE)))
    (SETQ CHAINAGE (SUBSTR DFCC_CHAINAGE (+ (VL-STRING-POSITION (ASCII "/") DFCC_CHAINAGE) 2)))
    (PUTCELLSHEET "PROIN" "F8" KM)
    (PUTCELLSHEET "PROIN" "F10" CHAINAGE)
    ;
    
    (SETQ LOC_DETAILS (PARAMETERS_EXTRACT "Implantation" "A5:A5" "B5:B5"))
    
    (SETQ LOC_DETAILS (RTOS (NTH 0 (SINGLE_ELE_LIST LOC_DETAILS 1)) 2 2))
    (IF (< (ATOF (NTH 0 (SINGLE_ELE_LIST (EXTRACT_ATTRIBUTES (NTH 0 (NTH I FILTERED_LIST)) (LIST "IMPLANTATION1" ) 1) 1))) 3.10)
    (MODIFY_ATTRIBUTES (NTH 0 (NTH I FILTERED_LIST)) (lIST "IMPLANTATION1") (LIST LOC_DETAILS))
    )
    (IF (= I (- (LENGTH FILTERED_LIST) 1)) (PROGN (SET_TILE "INFO" "FOUNDATIONS ARE UPDATED") (SET_TILE "PERCENTAGE" "CLICK OK TO VIEW RESULTS")))
    )
    )
    (SETQ I (+ I 1))
    (SETQ PER (/ (* (+ I 1) 100) (LENGTH FILTERED_LIST)))
    )
    (setq ddiag(start_dialog))
)




(DEFUN C:PRINT_LOC_DETAILS2 ( / )
   (SETQ BLOCKS_LIST (FORM_SSSET (SSGET "X" (LIST (CONS 0 "INSERT")))))
   (SETQ BLOCK_NAME_LIST (EXTRACT_ENTITY_INFO2 BLOCKS_LIST))
   (SETQ ENT_LIST (SINGLE_ELE_LIST (FILTER_LIST (LIST "SINGLE_CANT_MAST" "DOUBLE_CANT_MAST" "TRIPLE_CANT_MAST" "TTC" "SS0" "SS1" "SS2" "SS3" "SS4") BLOCK_NAME_LIST 1) 0))
   (SETQ STARTING_MAST (CAR(ENTSEL "N/ SELECT STARTING MAST")))
   (SETQ TRACK_CENTER (CAR(ENTSEL "N/ SELECT TRACK CENTER")))
   (SETQ STARTING_CELL (GETSTRING "N/ ENTER STARTING CELL"))
   ;(SETQ ENT_LIST (FORM_SSSET SSSET))
   (SETQ ENT_LIST (EXTRACT_ENTITY_INFO ENT_LIST 1 3))
   (SETQ ENT_LIST (SORT_MASTS ENT_LIST STARTING_MAST))
    (SETQ DETAILS_TO_PRINT (GET_CO-ORDINATES2 (SINGLE_ELE_LIST ENT_LIST 0)))
    (PUTCELLSHEET "Sheet1" (COLUMN+N STARTING_CELL 0) (SINGLE_ELE_LIST DETAILS_TO_PRINT 0))
    (PUTCELLSHEET "Sheet1" (COLUMN+N STARTING_CELL 1) (SINGLE_ELE_LIST DETAILS_TO_PRINT 1))
    (PUTCELLSHEET "Sheet1" (COLUMN+N STARTING_CELL 2) (SINGLE_ELE_LIST DETAILS_TO_PRINT 2))
    (PUTCELLSHEET "Sheet1" (COLUMN+N STARTING_CELL 3) (SINGLE_ELE_LIST DETAILS_TO_PRINT 3))
    (PUTCELLSHEET "Sheet1" (COLUMN+N STARTING_CELL 4) (SINGLE_ELE_LIST DETAILS_TO_PRINT 4))
    (PUTCELLSHEET "Sheet1" (COLUMN+N STARTING_CELL 5) (SINGLE_ELE_LIST DETAILS_TO_PRINT 5))
    (PUTCELLSHEET "Sheet1" (COLUMN+N STARTING_CELL 6) (SINGLE_ELE_LIST DETAILS_TO_PRINT 6))
    (PUTCELLSHEET "Sheet1" (COLUMN+N STARTING_CELL 7) (SINGLE_ELE_LIST DETAILS_TO_PRINT 7))
)



(DEFUN C:LOAD_EXCEL_GPS ( / )
  (OPENEXCEL (FINDFILE "SPANEXTRACT.XLSX") "Sheet1" T)
)

(DEFUN C:LOAD_OBSTRUCTION_FILE ( / )
  (OPENEXCEL (FINDFILE (GETFILED "SELECT OBSTRUCTION FILE" "" "" 8)) "Sheet1" T)
)

(DEFUN GET_CO-ORDINATES2 ( ENT_LIST  / ENT_LIST I TEMP_CHAINAGE TEMP_EFFNAME TEMP_SPAN FINAL_LIST)

  (SETQ I 0 TEMP_CHAINAGE NIL TEMP_EFFNAME NIL TEMP_SPAN NIL FINAL_LIST NIL)
  (WHILE (< I (LENGTH ENT_LIST))
    (SETQ TEMP_NUMBER (NTH 0 (SINGLE_ELE_LIST (EXTRACT_ATTRIBUTES (NTH I ENT_LIST) (LIST "MAST_NUMBER1" ) 1) 1)))
    (SETQ TEMP_CHAINAGE (NTH 0 (SINGLE_ELE_LIST (EXTRACT_ATTRIBUTES (NTH I ENT_LIST) (LIST "FOUNDATION_TYPE1" ) 1) 1)))
    (SETQ TEMP_MAST (NTH 0 (SINGLE_ELE_LIST (EXTRACT_ATTRIBUTES (NTH I ENT_LIST) (LIST "MAST_TYPE1" ) 1) 1)))
    (SETQ TEMP_IMP (NTH 0 (SINGLE_ELE_LIST (EXTRACT_ATTRIBUTES (NTH I ENT_LIST) (LIST "IMPLANTATION1" ) 1) 1)))
    (SETQ TEMP_EFFNAME (VLAX-GET-PROPERTY (VLAX-ENAME->VLA-OBJECT (NTH I ENT_LIST)) 'EFFECTIVENAME))
    (SETQ TEMP_SPAN (NTH 0 (SINGLE_ELE_LIST (EXTRACT_ATTRIBUTES (NTH I ENT_LIST) (LIST "SPAN1" ) 1) 1)))
    
    (SETQ FLIP (NTH 1 (NTH 0 (GET_DYNAMIC_PROPERTIES (NTH I ENT_LIST) '("STF1")))))
    
    (SETQ ROTATION (VLAX-GET-PROPERTY (VLAX-ENAME->VLA-OBJECT (NTH I ENT_LIST)) 'ROTATION))
    (SETQ TEMP_CO-ORDINATES (CDR (ASSOC 10 (ENTGET (NTH I ENT_LIST)))))
    (IF (= FLIP 0)
     (SETQ TEMP_CO-ORDINATES (MAPCAR 'RTOS (POLAR TEMP_CO-ORDINATES (+ (* 1 (/ PI 2)) ROTATION) (+ (- (ATOF TEMP_IMP) 3.00) 0.2))) TEMP_LINE "Dn Line")
     (SETQ TEMP_CO-ORDINATES (MAPCAR 'RTOS (POLAR TEMP_CO-ORDINATES (+ (* 3 (/ PI 2)) ROTATION) (+ (- (ATOF TEMP_IMP) 3.00) 0.2))) TEMP_LINE "Up Line")
    )
    (SETQ FINAL_LIST (CONS (APPEND (LIST TEMP_NUMBER TEMP_CHAINAGE TEMP_MAST TEMP_IMP TEMP_SPAN TEMP_LINE) TEMP_CO-ORDINATES) FINAL_LIST))
    (SETQ I (+ I 1))
  )
  (REVERSE FINAL_LIST)
  
)




(DEFUN C:UPDATE_CONVENTIONAL_FOUNDATION_DETAILS( / TOTAL_LIST LIST1 ENT_LIST I BLOCK_LIST FILTERED_LIST TEMP_LIST LOC_DETAILS PER)
(SETQ TOTAL_LIST (GET_TOTAL_LOC_LIST_GPS))
(SETQ BLOCKS_LIST (FORM_SSSET (SSGET "W" WPT1 WPT2 (LIST (CONS 0 "INSERT")))))
(SETQ TRACK_ENTITY_UPTRACK (ENTSEL "\nSELECT TRACK ALIGNMENT FOR UP TRACK (DN LINE):"))
(SETQ REF_MAST_DN (CAR (ENTSEL "\nSELECT REFERENCE MAST DNLINE:")))
(SETQ REF_MAST_UP (CAR (ENTSEL "\nSELECT REFERENCE MAST UPLINE:")))
(SETQ ATTRIBUTE_TAG_LIST (LIST "FOUNDATION_TYPE1" "RD1" "STEP_DISTANCE/EMBEDDED_LENGTH" "SUPER_BLOCK/EXTRA_DEPTH" "RADIUS/SUPER_ELEVATION" "DUMMY_VARIABLE2" "ANCHOR_BLOCK/ANCHOR_STEP/ANCHOR_SETTING_DISTANCE"))

  
   (setq dcl_id (load_dialog "DISPLAY_INFO.dcl"))
   (new_dialog "DISPLAY_INFO" dcl_id)
  
   
(SETQ FILTERED_LIST (APPEND (SINGLE_ELE_LIST TOTAL_LIST 0) (SINGLE_ELE_LIST TOTAL_LIST 1)))
  (SETQ I 0)
  (SETQ PER (/ (* (+ I 1) 100) (LENGTH FILTERED_LIST)))
  (SETQ TEMP_LIST NIL)
  (SETQ LOC_DETAILS NIL)
  
  (WHILE (< I (LENGTH FILTERED_LIST))
    (SET_TILE "INFO" (STRCAT "UPDATING FOUNDATION" " " (ITOA (+ I 1)) " " "OF" " "  (ITOA (LENGTH FILTERED_LIST))))
    (SET_TILE "PERCENTAGE" (STRCAT (RTOS PER 2 2) "%" " " "COMPLETED"))
    (IF (/= (NTH I FILTERED_LIST) NIL)
    (PROGN
    
    (SETQ TEMP_LIST (GET_DATA_TO_BE_FILLED2 (NTH I FILTERED_LIST)))
    (PUTCELLSHEET "PROIN" "F8" (NTH 0 TEMP_LIST))
    (SETQ DFCC_CHAINAGE (NTH 0 (SINGLE_ELE_LIST (EXTRACT_ATTRIBUTES (NTH 0 (NTH I FILTERED_LIST)) (LIST "CHAINAGE2" ) 1) 1)))
    (SETQ CONT_CHAINAGE (NTH 0 (SINGLE_ELE_LIST (EXTRACT_ATTRIBUTES (NTH 0 (NTH I FILTERED_LIST)) (LIST "CHAINAGE1" ) 1) 1)))
    (SETQ KM (SUBSTR DFCC_CHAINAGE 1 (VL-STRING-POSITION (ASCII "/") DFCC_CHAINAGE)))
    (SETQ CHAINAGE (SUBSTR DFCC_CHAINAGE (+ (VL-STRING-POSITION (ASCII "/") DFCC_CHAINAGE) 2)))
    (SETQ CONT_KM (SUBSTR CONT_CHAINAGE 1 (VL-STRING-POSITION (ASCII "/") CONT_CHAINAGE)))
    (PUTCELLSHEET "PROIN" "F8" KM)
    (PUTCELLSHEET "PROIN" "F10" CHAINAGE)
    (PUTCELLSHEET "PROIN" "K8" CONT_KM)
    (SETQ LOC_DETAILS (PARAMETERS_EXTRACT "Implantation" "A8:A14" "B8:B14"))
    (SETQ LOC_DETAILS (SINGLE_ELE_LIST LOC_DETAILS 1))   
    (MODIFY_ATTRIBUTES (NTH 0 (NTH I FILTERED_LIST)) (lIST "FOUNDATION_TYPE1" "RD1" "STEP_DISTANCE/EMBEDDED_LENGTH" "SUPER_BLOCK/EXTRA_DEPTH" "RADIUS/SUPER_ELEVATION" "DUMMY_VARIABLE2" "ANCHOR_BLOCK/ANCHOR_STEP/ANCHOR_SETTING_DISTANCE") LOC_DETAILS)
    ;(MODIFY_ATTRIBUTES (NTH 0 (NTH I FILTERED_LIST)) (lIST "RD1") (LIST (RTOS (NTH 1 LOC_DETAILS) 2 0)))
    
    (IF (= I (- (LENGTH FILTERED_LIST) 1)) (PROGN (SET_TILE "INFO" "FOUNDATIONS ARE UPDATED") (SET_TILE "PERCENTAGE" "CLICK OK TO VIEW RESULTS")))
    )
    )
    (SETQ I (+ I 1))
    (SETQ PER (/ (* (+ I 1) 100) (LENGTH FILTERED_LIST)))
    )
  (setq ddiag(start_dialog))
  (SETQ BLOCK_NAME_LIST (EXTRACT_ENTITY_INFO2 BLOCKS_LIST))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  (SETQ MAST_UP (FILTER_LIST '("UP") MAST_TTC_DIR 1))
  (SETQ MAST_DN (FILTER_LIST '("DN") MAST_TTC_DIR 1))
  (SETQ TOTAL_LIST (SINGLE_ELE_LIST (APPEND MAST_UP MAST_DN) 0))
  (SETQ I 0)
  (WHILE (< I (LENGTH TOTAL_LIST))
      (CHANGE_VISIBILITY (NTH I TOTAL_LIST) (LIST "FOUNDATION_TYPE1" "RD1" "STEP_DISTANCE/EMBEDDED_LENGTH" "SUPER_BLOCK/EXTRA_DEPTH" "RADIUS/SUPER_ELEVATION" "DUMMY_VARIABLE2" "ANCHOR_BLOCK/ANCHOR_STEP/ANCHOR_SETTING_DISTANCE") (LIST "1" "1" "1" "1" "1" "1" "1"))
      (SETQ  I (+ I 1))
  )
  
  ;(SETQ MAST_UP (SORT_ENTITIES_ALONG_CURVE1 (VLAX-ENAME->VLA-OBJECT (NTH 0 TRACK_ENTITY_UPTRACK)) MAST_UP (LIST 1 STARTING_POINT) 0 1))
  ;(SETQ MAST_DN (SORT_ENTITIES_ALONG_CURVE1 (VLAX-ENAME->VLA-OBJECT (NTH 0 TRACK_ENTITY_UPTRACK)) MAST_DN (LIST 1 STARTING_POINT) 0 1))

  (SETQ I 0)
  (WHILE (< I (LENGTH ATTRIBUTE_TAG_LIST))
      (MATCH_POSITION1 REF_MAST_UP (SINGLE_ELE_LIST MAST_UP 0) (NTH I ATTRIBUTE_TAG_LIST))
      (MATCH_POSITION1 REF_MAST_DN (SINGLE_ELE_LIST MAST_DN 0) (NTH I ATTRIBUTE_TAG_LIST))
      (SETQ  I (+ I 1))
  )
     
)
