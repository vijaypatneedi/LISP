(DEFUN C:CHANGE_CONTINUOUS_CHAINAGES ( / )

(SETQ BLOCKS_LIST (FORM_SSSET (SSGET "X" (LIST (CONS 8 "OHE-TXT-OBS CONT CHAINAGE")))))

(SETQ I 0 TEMP_ELE NIL FINAL_LIST NIL)

(WHILE (< I (LENGTH BLOCKS_LIST))

(SETQ ENTNAME (NTH I BLOCKS_LIST))

(SETQ ST_CH (CDR (ASSOC 1 (ENTGET ENTNAME))))

(IF (/= (VL-STRING-POSITION (ASCII ":") ST_CH) NIL)

(PROGN
(SETQ	TOT_CH	(SUBSTR	ST_CH (+ (VL-STRING-POSITION (ASCII ":") ST_CH) 2)))

(SETQ	KM_NO (SUBSTR TOT_CH 1 (VL-STRING-POSITION (ASCII "/") TOT_CH)))

(SETQ	CH	(SUBSTR	TOT_CH (+ (VL-STRING-POSITION (ASCII "/") TOT_CH) 2)))

(SETQ	CH (SUBSTR CH 1 (VL-STRING-POSITION (ASCII "(") CH)))



(SETQ FINAL_CHAINAGE (+ (+ (* (ATOF KM_NO) 1000) (ATOF CH)) 21))

(SETQ FINAL_KM (FIX (/ FINAL_CHAINAGE 1000)))

(SETQ FINAL_CH (RTOS (- FINAL_CHAINAGE (* (FIX (/ FINAL_CHAINAGE 1000)) 1000)) 2 2))


(SETQ FINAL_CHAINAGE (STRCAT "CH:" (RTOS FINAL_KM 2 0) "/" FINAL_CH " (CONT.)"))

(VLAX-PUT-PROPERTY (VLAX-ENAME->VLA-OBJECT ENTNAME) 'TextString FINAL_CHAINAGE)
(SETQ FINAL_LIST (CONS (LIST ST_CH FINAL_CHAINAGE) FINAL_LIST))

)
  
(SETQ FINAL_LIST (CONS (LIST ST_CH " ") FINAL_LIST))

)




(SETQ I (+ I 1))

)

(PUTCELLSHEET "Sheet1" (COLUMN+N "A2" 0) (SINGLE_ELE_LIST (REVERSE FINAL_LIST) 0))
(PUTCELLSHEET "Sheet1" (COLUMN+N "A2" 1) (SINGLE_ELE_LIST (REVERSE FINAL_LIST) 1))


)
