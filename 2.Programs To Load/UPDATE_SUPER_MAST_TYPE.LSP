(DEFUN C:UPDATE_SUPERMAST_TYPE( / TOTAL_LIST LIST1 ENT_LIST I BLOCK_LIST FILTERED_LIST TEMP_LIST LOC_DETAILS PER)
(SETQ TOTAL_LIST (GET_TOTAL_LOC_LIST_GPS))
(SETQ BLOCKS_LIST (FORM_SSSET (SSGET "W" WPT1 WPT2 (LIST (CONS 0 "INSERT")))))
(SETQ TRACK_ENTITY_UPTRACK (ENTSEL "\nSELECT TRACK ALIGNMENT FOR UP TRACK (DN LINE):"))
(SETQ STARTING_POINT (GETPOINT "\nPICK STARTING POINT"))

(setq dcl_id (load_dialog "DISPLAY_INFO.dcl"))
(new_dialog "DISPLAY_INFO" dcl_id)

(SETQ DNMAIN_MASTS  (SORT_ENTITIES_ALONG_CURVE1 (NTH 0 TRACK_ENTITY_UPTRACK) (REMOVE_NIL (SINGLE_ELE_LIST TOTAL_LIST 0)) (LIST 1 STARTING_POINT) 0 1))
(SETQ UPMAIN_MASTS  (SORT_ENTITIES_ALONG_CURVE1 (NTH 0 TRACK_ENTITY_UPTRACK) (REMOVE_NIL (SINGLE_ELE_LIST TOTAL_LIST 1)) (LIST 1 STARTING_POINT) 0 1))
   
  (SETQ I 0)
  (SETQ TEMP_LIST NIL)
  (SETQ TEMP_LIST1 NIL TEMP_LIST2 NIL TEMP_LIST3 NIL TEMP_LIST4 NIL)
  (SETQ LOC_DETAILS NIL)
  (SET_TILE "INFO" "UPDATING SUPER MAST TYPE")
  (SET_TILE "PERCENTAGE" "PLEASE WAIT...")
  
  (WHILE (< I (LENGTH DNMAIN_MASTS))
    
    (IF (/= (NTH I DNMAIN_MASTS) NIL)
    (PROGN
    
    (SETQ TEMP_LIST1 (NTH 0 (GET_DATA_TO_BE_FILLED2 (NTH I DNMAIN_MASTS))))
    (IF (/= (NTH 1 (NTH I DNMAIN_MASTS)) NIL) (MODIFY_ATTRIBUTES (NTH 1 (NTH I DNMAIN_MASTS)) (lIST"SUPER_MAST_TYPE" "CROSS_ARM_TYPE" "SM") (LIST "1" "1" "2X25KV NEW")))
    (IF (/= I 0) (SETQ TEMP_LIST3 (NTH 0 (GET_DATA_TO_BE_FILLED2 (NTH (- I 1) DNMAIN_MASTS)))) (SETQ TEMP_LIST3 NIL))
    (IF (/= I (+ (LENGTH DNMAIN_MASTS) 1)) (SETQ TEMP_LIST4 (NTH 0 (GET_DATA_TO_BE_FILLED2 (NTH (+ I 1) DNMAIN_MASTS)))) (SETQ TEMP_LIST4 NIL))
    (SETQ FLAG 0)
    (IF (AND (/= I 0) (/= I (- (LENGTH DNMAIN_MASTS) 1)))
    (PROGN
    (IF (OR (= (NTH 6 TEMP_LIST3) (NTH 33 TEMP_LIST3)) (= (NTH 6 TEMP_LIST4) (NTH 33 TEMP_LIST4))) (SETQ FLAG 1))
    (IF (OR (= (NTH 36 TEMP_LIST3) "FA") (= (NTH 36 TEMP_LIST4) "FA")) (SETQ FLAG 1))
    )
    )
    (IF (/= (NTH 36 TEMP_LIST1) "FA")
    (PROGN
    (IF (= (NTH 6 TEMP_LIST1) (NTH 33 TEMP_LIST1))     
    (MODIFY_ATTRIBUTES (NTH 1 (NTH I DNMAIN_MASTS)) (lIST"SUPER_MAST_TYPE" "CROSS_ARM_TYPE" "SM") (LIST "1.5" "1.1" "2X25KV"))
    (PROGN
      (IF (= FLAG 1) (MODIFY_ATTRIBUTES (NTH 1 (NTH I DNMAIN_MASTS)) (lIST"SUPER_MAST_TYPE" "CROSS_ARM_TYPE" "SM") (LIST "1.5" "1.1" "2X25KV")))
    )
    )
    )
    )  
    )
    )
    (SETQ I (+ I 1))
    
    )


  (SETQ I 0)
  (SETQ TEMP_LIST NIL)
  (SETQ TEMP_LIST1 NIL TEMP_LIST2 NIL TEMP_LIST3 NIL TEMP_LIST4 NIL)
  (SETQ LOC_DETAILS NIL)
  (WHILE (< I (LENGTH UPMAIN_MASTS))
    
    (IF (/= (NTH I UPMAIN_MASTS) NIL)
    (PROGN
    
    
    (SETQ TEMP_LIST2 (NTH 0 (GET_DATA_TO_BE_FILLED2 (NTH I UPMAIN_MASTS))))
    (IF (/= (NTH 1 (NTH I UPMAIN_MASTS)) NIL) (MODIFY_ATTRIBUTES (NTH 1 (NTH I UPMAIN_MASTS)) (lIST"SUPER_MAST_TYPE" "CROSS_ARM_TYPE" "SM") (LIST "1.5" "1.1" "2X25KV NEW")))
    

    (IF (/= I 0) (SETQ TEMP_LIST3 (NTH 0 (GET_DATA_TO_BE_FILLED2 (NTH (- I 1) UPMAIN_MASTS)))) (SETQ TEMP_LIST3 NIL))
    (IF (/= I (+ (LENGTH UPMAIN_MASTS) 1)) (SETQ TEMP_LIST4 (NTH 0 (GET_DATA_TO_BE_FILLED2 (NTH (+ I 1) UPMAIN_MASTS)))) (SETQ TEMP_LIST4 NIL))
    (SETQ FLAG 0)
    (IF (AND (/= I 0) (/= I (- (LENGTH UPMAIN_MASTS) 1)))
    (PROGN
    (IF (OR (= (NTH 6 TEMP_LIST3) (NTH 33 TEMP_LIST3)) (= (NTH 6 TEMP_LIST4) (NTH 33 TEMP_LIST4))) (SETQ FLAG 1))
    (IF (OR (= (NTH 36 TEMP_LIST3) "FA") (= (NTH 36 TEMP_LIST4) "FA")) (SETQ FLAG 1))
    )
    )
    (IF (/= (NTH 36 TEMP_LIST2) "FA")
    (PROGN
    (IF (= (NTH 6 TEMP_LIST2) (NTH 33 TEMP_LIST2))   
    (MODIFY_ATTRIBUTES (NTH 1 (NTH I UPMAIN_MASTS)) (lIST"SUPER_MAST_TYPE" "CROSS_ARM_TYPE" "SM") (LIST "1.5" "1.1" "2X25KV"))
    (PROGN
      (IF (= FLAG 1) (MODIFY_ATTRIBUTES (NTH 1 (NTH I UPMAIN_MASTS)) (lIST"SUPER_MAST_TYPE" "CROSS_ARM_TYPE" "SM") (LIST "1.5" "1.1" "2X25KV")))
    )
    )
    )
    )
    )
    )
    (SETQ I (+ I 1))
    )

  (SET_TILE "INFO" "DONE....!!!")
  (SET_TILE "PERCENTAGE" "PRESS OK")
  
  (setq ddiag(start_dialog))
   
)
