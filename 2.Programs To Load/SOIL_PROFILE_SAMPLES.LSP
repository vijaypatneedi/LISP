(DEFUN C:CREATE_SAMPLES ( / )
  (SETQ LIST1 (EXTRACT_DATA_EXCEL "A1:A10" "E1:E10"))
  (SETQ I 1)
  (SETQ FIRST_SAMPLE (NTH 0 LIST1))
  (WHILE (< I (LENGTH LIST1))
    (IF (TEST_SAMPLE FIRST_SAMPLE (NTH I LIST1))
      (PROGN
	(SETQ I (+ I 1))
	)
      (PROGN
	(SETQ FINAL_LIST (CONS (LIST (LIST (NTH 0 FIRST_SAMPLE) (NTH 0 (NTH I LIST1))) (CDR FIRST_SAMPLE)) FINAL_LIST))
	(SETQ FIRST_SAMPLE (NTH I LIST1))
	(SETQ I (+ I 1))
      )

    )
   )
  (REVERSE FINAL_LIST)
)


(DEFUN INCREMENT_RANGE (RANGE FLAG / CELLVALUES FLAG FINAL_RANGE)
  (SETQ CELLVALUES (STRING_BREAK RANGE ":"))
  (IF (= FLAG "C")
    (SETQ FINAL_RANGE
	   (LIST (COLUMN+N (NTH 0 CELLVALUES) 1)
		 (COLUMN+N (NTH 1 CELLVALUES) 1)
	   )
    )
    (SETQ FINAL_RANGE
	   (LIST (ROW+N (NTH 0 CELLVALUES) 1)
		 (ROW+N (NTH 1 CELLVALUES) 1)
	   )
    )
  )
  (REVERSE FINAL_RANGE)
)


(DEFUN EXTRACT_DATA_EXCEL (FIRST_RANGE SECOND_RANGE / )
  (SETQ I 0)
  
  (SETQ SECOND_RANGE (INCREMENT_RANGE SECOND_RANGE "C"))
  (SETQ TEMP_RANGE (INCREMENT_RANGE FIRST_RANGE "C") FINAL_LIST (getCellsrow/column "Sheet1" FIRST_RANGE))
  (WHILE (/= TEMP_RANGE SECOND_RANGE)
    (IF (= TEMP_RANGE (INCREMENT_RANGE FIRST_RANGE "C"))
      (SETQ FINAL_LIST (ADD_LISTS1 FINAL_LIST (getCellsrow/column "Sheet1" (STRCAT (NTH 0 TEMP_RANGE) ":" (NTH 1 TEMP_RANGE)) )))
      (SETQ FINAL_LIST (ADD_LISTS FINAL_LIST (getCellsrow/column "Sheet1" (STRCAT (NTH 0 TEMP_RANGE) ":" (NTH 1 TEMP_RANGE)) )))
    )
  )
  FINAL_LIST
)
    
    




(DEFUN REP_REMOVE (LIST1 / TEMP_ELE TEMP_LIST NEW_LIST)
  (SETQ TEMP_LIST LIST1)
  (SETQ NEW_LIST NIL)
  (WHILE (/= TEMP_LIST NIL)
    (SETQ TEMP_ELE (CAR TEMP_LIST))
    (SETQ TEMP_LIST (VL-REMOVE TEMP_ELE TEMP_LIST))
    (SETQ NEW_LIST (CONS TEMP_ELE NEW_LIST))
  )
  (SETQ NEW_LIST (REVERSE NEW_LIST))
)

(DEFUN SUBSTRACTION (LIST1 LIST2 / I TEMP_ELE LIST3)

  (SETQ I 0)
  (SETQ TEMP_ELE NIL)
  (SETQ LIST3 NIL)
  (WHILE (< I (LENGTH LIST1))
    (SETQ TEMP_ELE (- (NTH I LIST1) (NTH I LIST2)))
    (SETQ LIST3 (CONS TEMP_ELE LIST3))
    (SETQ I (+ I 1))
  )
  (REVERSE LIST3)
)



(DEFUN TEST_SAMPLE (FIRST_SAMPLE SAMPLE_TO_TEST / )
  (SETQ LIST_TO_TEST (SUBSTRACTION (CDR FIRST_SAMPLE) (CDR SAMPLE_TO_TEST)))
  (SETQ LIST_TO_TEST (REP_REMOVE (MAPCAR '(LAMBDA (X) (> X  0.1)) LIST_TO_TEST)))
  (SETQ AWNSER NIL)
  (IF ( = (LENGTH LIST_TO_TEST) 1)
    (SETQ AWNSER (NTH 0 LIST_TO_TEST))
  )
  AWNSER
)
