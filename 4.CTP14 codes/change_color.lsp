(defun c:change_color()
 (command "dist")
 ;(setq pt (getvar "lastpoint"))
 ;(setq ssPt (ssget pt))
 ;(setq ent (ssname sspt 0))
 (setq ent (nth 0 (entsel)))
 (setq list1 (entget ent))
 (setq list1 (append list1 (list (cons 62 3))))
 (entmod list1)
 (entupd ent)
 )
