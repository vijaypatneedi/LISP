(defun c:CHAINAGES_YARD () ;;;;;;;;;;;;;;;;;;;;;;;;;;;;;;;;;;;;;;;;;;;;;;;;;;;;;;;;;;;;;;;;;;;;TO UPDATE THE CHAINAGES OF BLOCKS
(setq MODE (GETSTRING "ENTER MODE OF OPERATION : MANUAL->M | AUTOMATIC->A"))
(IF (= MODE "A")
(PROGN
(setq WPT1 (GETPOINT "\n PICK POINT1"))
(setq WPT2 (GETPOINT "\n PICK POINT2"))
(setq WPT3 (GETPOINT "\n PICK POINT3"))
(setq WPT4 (GETPOINT "\n PICK POINT4"))
(YARD_MAST_DATA WPT1 WPT2 WPT3 WPT4)
(setq BLOCK_LIST MAST_LIST)
)(PROGN
(setq BREAK_CH (getdist "Enter Break Chainage: "))
)
)
;(setq KM_STONE (entsel "Select DFCC KM Stone :"))
;(setq CTNKM_STONE (entsel "Select CTN KM Stone :"))
(IF (= KM_STONE NIL)
(PROGN
(ALERT "pLEASE SELECT TRACK ENTITY FIRST")
)
)
(setq KM_STONE_CORD (list (getpropertyvalue (car KM_STONE) "Position/X") (getpropertyvalue (car KM_STONE) "Position/Y") 0.0))
(setq CTNKM_STONE_CORD (list (getpropertyvalue (car CTNKM_STONE) "Position/X") (getpropertyvalue (car CTNKM_STONE) "Position/Y") 0.0))
(setq KM_STONE_PROJ (vlax-curve-getClosestPointTo TRACK KM_STONE_CORD T))
(setq CTNKM_STONE_PROJ (vlax-curve-getClosestPointTo TRACK CTNKM_STONE_CORD T))
(setq KM_DIST (vlax-curve-getDistAtPoint TRACK KM_STONE_PROJ))
(setq CTNKM_DIST (vlax-curve-getDistAtPoint TRACK CTNKM_STONE_PROJ))
(setq DFCC_KM_VAL (substr (getpropertyvalue (car KM_STONE) "KM") 7))
(setq CTN_KM_VAL (substr (getpropertyvalue (car CTNKM_STONE) "KM") 12)) ; CALIBRATE HERE
(setq I 0)
(while (IF (= MODE "M") (PROGN (> 1 0))(PROGN (< I (LENGTH BLOCK_LIST))))
(IF (= MODE "M")
(PROGN
(setq BLOCK (entsel "Select the BLOCK : "))
)
)
(IF (= MODE "A")
(PROGN
(setq BLOCK (LIST (NTH I BLOCK_LIST)))
(setq BREAK_CH 0)
)
)
(setq BLOCK_CORD (list (getpropertyvalue (car BLOCK) "Position/X") (getpropertyvalue (car BLOCK) "Position/Y") 0.0))
(setq BLOCK_PROJ (vlax-curve-getClosestPointTo TRACK BLOCK_CORD T))
(setq BLOCK_DIST (vlax-curve-getDistAtPoint TRACK BLOCK_PROJ))
(setq DFCC_CH (round (+ (- BLOCK_DIST KM_DIST) BREAK_CH) 0.5))
(setq DFCC_X (fix (/ DFCC_CH 1000)))
(if (< DFCC_CH 0)
(PROGN
(SETQ DFCC_CH (+ 1000 DFCC_CH))
(SETQ DFCC_X (- DFCC_X 1))
)
)
(setq CTN_CH (round (- BLOCK_DIST CTNKM_DIST) 0.5))
(setq CTN_X (fix (/ CTN_CH 1000)))
(if (< CTN_CH 0)
(PROGN
(SETQ CTN_CH (+ 1000 CTN_CH))
(SETQ CTN_X (- CTN_X 1))
)
)
(setq BLOCK_NAME (getpropertyvalue (car BLOCK) "BlockTableRecord/Name"))
(IF(= BLOCK_NAME "PORTAL")
(PROGN
(setq CS_PORTAL (round (getpropertyvalue (car BLOCK) "AcDbDynBlockPropertySTL1") 0.05))
(setq X_TYPE_PORTAL (GET_ATTRIBUTE_VALUE "MAST_TYPE1" (CAR BLOCK)))
(IF (= X_TYPE_PORTAL "G-TYPE")
(PROGN
(setq TYPE_PORTAL "G-TYPE")
)
(PROGN
(setq TYPE_PORTAL (GET_PORTAL_TYPE CS_PORTAL))
(if (= TYPE_PORTAL NIL)
(PROGN
(setpropertyvalue (CAR BLOCK) "Color" "6")
(Alert "Portal type is Out of List at the Magenta portal")
)
)
)
)
(MODIFY_ATTRIBUTES (CAR BLOCK) (LIST "CHAINAGE3" "CHAINAGE4" "CHAINAGE1" "CHAINAGE2" "CS1" "CS2" "MAST_TYPE1" "MAST_TYPE2") (LIST (STRCAT (ITOA (+ (ATOI DFCC_KM_VAL) DFCC_X)) "/" (RTOS (- DFCC_CH (* DFCC_X 1000)) 2 2)) (STRCAT (ITOA (+ (ATOI DFCC_KM_VAL) DFCC_X)) "/" (RTOS (- DFCC_CH (* DFCC_X 1000)) 2 2)) (STRCAT (ITOA (+ (ATOI CTN_KM_VAL) CTN_X)) "/" (RTOS (- CTN_CH (* CTN_X 1000)) 2 2)) (STRCAT (ITOA (+ (ATOI CTN_KM_VAL) CTN_X)) "/" (RTOS (- CTN_CH (* CTN_X 1000)) 2 2)) (strcat "CS-" (RTOS CS_PORTAL 2 2)) (strcat "CS-" (RTOS CS_PORTAL 2 2)) TYPE_PORTAL TYPE_PORTAL))
;(setpropertyvalue (CAR BLOCK) "Color" "1")
)
)
(IF(OR (= BLOCK_NAME "SS0") (= BLOCK_NAME "TRIPLE_CANT_MAST") (= BLOCK_NAME "DOUBLE_CANT_MAST") (= BLOCK_NAME "SINGLE_CANT_MAST") (= BLOCK_NAME "TTC"))
(PROGN
(MODIFY_ATTRIBUTES (CAR BLOCK) (LIST "CHAINAGE2" "CHAINAGE1") (LIST (STRCAT (ITOA (+ (ATOI DFCC_KM_VAL) DFCC_X)) "/" (RTOS (- DFCC_CH (* DFCC_X 1000)) 2 2)) (STRCAT (ITOA (+ (ATOI CTN_KM_VAL) CTN_X)) "/" (RTOS (- CTN_CH (* CTN_X 1000)) 2 2))))
;(setpropertyvalue (CAR BLOCK) "Color" "1")
)
)
(IF (OR(= BLOCK_NAME "SIGNAL_NEW") (= BLOCK_NAME "HYBRID_SIGNAL4") (= BLOCK_NAME "REPRESENTATION1") (= BLOCK_NAME "CURVE_SYMBOL1") (= BLOCK_NAME "GRADIENT_POST") (= BLOCK_NAME "SHUNT_SIGNAL") (= BLOCK_NAME "REPRESENTATION12"))
(PROGN
(setq DFCC_CH (+ (- BLOCK_DIST KM_DIST) BREAK_CH))
(setq CTN_CH (- BLOCK_DIST CTNKM_DIST))
(MODIFY_ATTRIBUTES (CAR BLOCK) (LIST "TEXT1" "TEXT3" ) (LIST (STRCAT "DFCC CH: " (ITOA (+ (ATOI DFCC_KM_VAL) DFCC_X)) "/" (RTOS (- DFCC_CH (* DFCC_X 1000)) 2 2)) (STRCAT "CONT CH: "(ITOA (+ (ATOI CTN_KM_VAL) CTN_X)) "/" (RTOS (- CTN_CH (* CTN_X 1000)) 2 2))))
(setpropertyvalue (CAR BLOCK) "Color" "1")
)
)
(IF (= MODE "A")
(PROGN
(setq I (+ 1 I))
)
)
)
)
(defun round (value to) ;TO ROUND OFF THE VALUES
  (setq to (abs to))
  (* to (fix (/ ((if (minusp value) - +) value (* to 0.5)) to)))
)
(defun c:TENSION_LENGTH( / wire pt1 pt2 pt3 pt4 pt5 pt6 pt7 pt8 i j P TO_ANCH_LIST FROM_ANCH_LIST) ;;;;;;;;;;;;;;;;;;;;;;;;;;;;;;;;;;;;;;;;;;;;;;;;;;;;;;;;;;;;;TO UPDATE THE TENSION LENGTH BLOCKS MANUALLY
(setq upINSTRACK (car (entsel "Select up main side insertion line : ")))
(setq dnINSTRACK (car (entsel "Select dn main side insertion line : ")))
(setq TO_ANCH_LIST NIL)
(setq FROM_ANCH_LIST NIL)
;;;;;;;;;;;;;;;;;
; (setq WPT1 (GETPOINT "\n PICK POINT1"))
; (setq WPT2 (GETPOINT "\n PICK POINT2"))
; (setq WPT3 (GETPOINT "\n PICK POINT3"))
; (setq WPT4 (GETPOINT "\n PICK POINT4"))
(setq WPT1 (nth 0 (POLYLINE_POINTS  big_RECTANGLE)))
(setq WPT2 (nth 1 (POLYLINE_POINTS  BIG_RECTANGLE)))
(setq WPT3 (nth 2 (POLYLINE_POINTS  BIG_RECTANGLE)))
(setq WPT4 (nth 3 (POLYLINE_POINTS  BIG_RECTANGLE)))
(YARD_MAST_DATA WPT1 WPT2 WPT3 WPT4)
(SETQ TOT_WIRES (GETINT "ENTER THE TOTAL NUMBER OF WIRE_RUNS"))
(setq WL_ANCHOR_LIST nil)
(setq ANCHORS_LIST (GET_BLOCK_LIST "ANCHOR"))
(setq i 0)
(while (< i (length ANCHORS_LIST))
(IF (= (SUBSTR (GET_ATTRIBUTE_VALUE "ACTUAL_WIRE_RUN1" (nth i ANCHORS_LIST)) 1 2) "WL")
(PROGN
(SETQ WL_ANCHOR_LIST (APPEND WL_ANCHOR_LIST (LIST (nth i ANCHORS_LIST))))
)
)
(setq i (+ 1 i))
)
(setq j 1)
(WHILE (< j (+ 1 TOT_WIRES))
(setq p 0)
(while (< p (length WL_ANCHOR_LIST))
(if (and (= j (READ (SUBSTR (GET_ATTRIBUTE_VALUE "ACTUAL_WIRE_RUN1" (nth p WL_ANCHOR_LIST)) 4 2))) (= (getpropertyvalue (nth p WL_ANCHOR_LIST) "AcDbDynBlockPropertyANF1") 0)) 
(progn
(setq FROM_ANCH_LIST (APPEND FROM_ANCH_LIST (list (nth p WL_ANCHOR_LIST))))
)
)
(if (and (= j (READ (SUBSTR (GET_ATTRIBUTE_VALUE "ACTUAL_WIRE_RUN1" (nth p WL_ANCHOR_LIST)) 4 2))) (= (getpropertyvalue (nth p WL_ANCHOR_LIST) "AcDbDynBlockPropertyANF1") 1)) 
(progn
(setq TO_ANCH_LIST (APPEND TO_ANCH_LIST (list (nth p WL_ANCHOR_LIST))))
)
)
(setq p (+ 1 p))
)
(setq j (+ 1 j))
)
;;;;;;;;;;;;;;;;;;;;;;;;;;
(setq FROM_ANCH nil)
(setq TO_ANCH nil)
(setq w 0)
(WHILE (< w (max (length TO_ANCH_LIST) (length FROM_ANCH_LIST)))
;(setq FROM_ANCH (entsel "Select FROM ANCHOR : "))
;(setq TO_ANCH (entsel "Select TO ANCHOR : "))
(setq FROM_ANCH (list (nth w FROM_ANCH_LIST)))
(setq TO_ANCH (list (nth w TO_ANCH_LIST)))
(if (and (/= FROM_ANCH NIL) (/= TO_ANCH NIL))
(PROGN
(setq FROM_LOC (GET_ATTRIBUTE_VALUE "ANCHOR_MAST_NO" (car FROM_ANCH)))
(setq FROM_CH (GET_ATTRIBUTE_VALUE "ANCHOR_CHAINAGE" (car FROM_ANCH)))
(setq TO_LOC (GET_ATTRIBUTE_VALUE "ANCHOR_MAST_NO" (car TO_ANCH)))
(setq TO_CH (GET_ATTRIBUTE_VALUE "ANCHOR_CHAINAGE" (car TO_ANCH)))
(setq FROM_ROT (VLAX-GET-PROPERTY (VLAX-ENAME->VLA-OBJECT (CAR FROM_ANCH)) 'ROTATION))
(setq TO_ROT (VLAX-GET-PROPERTY (VLAX-ENAME->VLA-OBJECT (CAR TO_ANCH)) 'ROTATION))
(setq FROM_CORD (list (getpropertyvalue (car FROM_ANCH) "Position/X") (getpropertyvalue (car FROM_ANCH) "Position/Y") 0.0))
(setq TO_CORD (list (getpropertyvalue (car TO_ANCH) "Position/X") (getpropertyvalue (car TO_ANCH) "Position/Y") 0.0))
(setq FROM_PROJ (vlax-curve-getClosestPointTo TRACK FROM_CORD T))
(setq TO_PROJ (vlax-curve-getClosestPointTo TRACK TO_CORD T))
(setq FROM_DIST (vlax-curve-getDistAtPoint TRACK FROM_PROJ))
(setq TO_DIST (vlax-curve-getDistAtPoint TRACK TO_PROJ))
(setq TL (round (- TO_DIST FROM_DIST) 0.5))
(setq from_dist_down (distance (vlax-curve-getClosestPointTo TRACK FROM_CORD T) from_cord))
(setq from_dist_up (distance (vlax-curve-getClosestPointTo up_TRACK FROM_CORD T) from_cord))
(setq to_dist_down (distance (vlax-curve-getClosestPointTo TRACK to_CORD T) to_cord))
(setq to_dist_up (distance (vlax-curve-getClosestPointTo up_TRACK to_CORD T) to_cord))
(if (> from_dist_down from_dist_up)
(progn
(setq INSFROM (vlax-curve-getClosestPointTo upINSTRACK FROM_CORD T))
(setq from_v_flip 1)
)
(progn
(setq INSFROM (vlax-curve-getClosestPointTo dnINSTRACK FROM_CORD T))
(setq from_v_flip 0)
)
)
(if (> to_dist_down to_dist_up)
(progn
(setq INSTO (vlax-curve-getClosestPointTo upINSTRACK TO_CORD T))
(setq to_v_flip 1)
)
(progn
(setq INSTO (vlax-curve-getClosestPointTo dnINSTRACK TO_CORD T))
(setq to_v_flip 0)
)
)
(command "INSERT" "TENSION_LENGTH" INSFROM 1 0)
(MODIFY_ATTRIBUTES (entlast) (LIST "TENSION_LENGTH" "LOCATION_NUM" "CHAINAGE") (LIST (RTOS TL 2 2) TO_LOC TO_CH))
(setpropertyvalue (entlast) "rotation" FROM_ROT)
(setpropertyvalue (entlast) "AcDbDynBlockPropertyTLF2" 1)
(setpropertyvalue (entlast) "AcDbDynBlockPropertyTLF1" from_v_flip)
(command "INSERT" "TENSION_LENGTH" INSTO 1 0)
(MODIFY_ATTRIBUTES (entlast) (LIST "TENSION_LENGTH" "LOCATION_NUM" "CHAINAGE") (LIST (RTOS TL 2 2) FROM_LOC FROM_CH))
(setpropertyvalue (entlast) "rotation" to_ROT)
(setpropertyvalue (entlast) "AcDbDynBlockPropertyTLF2" 0)
(setpropertyvalue (entlast) "AcDbDynBlockPropertyTLF1" to_v_flip)
)
)
(setq w (+ w 1))
)
)
(defun C:TENSION_LENGTH_MANUAL (/)
(setq upINSTRACK (car (entsel "Select up main side insertion line : ")))
(setq dnINSTRACK (car (entsel "Select dn main side insertion line : ")))
(while (> 1 0)
(setq FROM_ANCH (entsel "Select FROM ANCHOR : "))
(setq TO_ANCH (entsel "Select TO ANCHOR : "))
;(setq FROM_ANCH (list (nth w FROM_ANCH_LIST)))
;(setq TO_ANCH (list (nth w TO_ANCH_LIST)))
(if (and (/= FROM_ANCH NIL) (/= TO_ANCH NIL))
(PROGN
(setq FROM_LOC (GET_ATTRIBUTE_VALUE "ANCHOR_MAST_NO" (car FROM_ANCH)))
(setq FROM_CH (GET_ATTRIBUTE_VALUE "ANCHOR_CHAINAGE" (car FROM_ANCH)))
(setq TO_LOC (GET_ATTRIBUTE_VALUE "ANCHOR_MAST_NO" (car TO_ANCH)))
(setq TO_CH (GET_ATTRIBUTE_VALUE "ANCHOR_CHAINAGE" (car TO_ANCH)))
(setq FROM_ROT (VLAX-GET-PROPERTY (VLAX-ENAME->VLA-OBJECT (CAR FROM_ANCH)) 'ROTATION))
(setq TO_ROT (VLAX-GET-PROPERTY (VLAX-ENAME->VLA-OBJECT (CAR TO_ANCH)) 'ROTATION))
(setq FROM_CORD (list (getpropertyvalue (car FROM_ANCH) "Position/X") (getpropertyvalue (car FROM_ANCH) "Position/Y") 0.0))
(setq TO_CORD (list (getpropertyvalue (car TO_ANCH) "Position/X") (getpropertyvalue (car TO_ANCH) "Position/Y") 0.0))
(setq FROM_PROJ (vlax-curve-getClosestPointTo TRACK FROM_CORD T))
(setq TO_PROJ (vlax-curve-getClosestPointTo TRACK TO_CORD T))
(setq FROM_DIST (vlax-curve-getDistAtPoint TRACK FROM_PROJ))
(setq TO_DIST (vlax-curve-getDistAtPoint TRACK TO_PROJ))
(setq TL (round (- TO_DIST FROM_DIST) 0.5))
(setq from_dist_down (distance (vlax-curve-getClosestPointTo TRACK FROM_CORD T) from_cord))
(setq from_dist_up (distance (vlax-curve-getClosestPointTo up_TRACK FROM_CORD T) from_cord))
(setq to_dist_down (distance (vlax-curve-getClosestPointTo TRACK to_CORD T) to_cord))
(setq to_dist_up (distance (vlax-curve-getClosestPointTo up_TRACK to_CORD T) to_cord))
(if (> from_dist_down from_dist_up)
(progn
(setq INSFROM (vlax-curve-getClosestPointTo upINSTRACK FROM_CORD T))
(setq from_v_flip 1)
)
(progn
(setq INSFROM (vlax-curve-getClosestPointTo dnINSTRACK FROM_CORD T))
(setq from_v_flip 0)
)
)
(if (> to_dist_down to_dist_up)
(progn
(setq INSTO (vlax-curve-getClosestPointTo upINSTRACK TO_CORD T))
(setq to_v_flip 1)
)
(progn
(setq INSTO (vlax-curve-getClosestPointTo dnINSTRACK TO_CORD T))
(setq to_v_flip 0)
)
)
(command "INSERT" "TENSION_LENGTH" INSFROM 1 0)
(MODIFY_ATTRIBUTES (entlast) (LIST "TENSION_LENGTH" "LOCATION_NUM" "CHAINAGE") (LIST (RTOS TL 2 2) TO_LOC TO_CH))
(setpropertyvalue (entlast) "rotation" FROM_ROT)
(setpropertyvalue (entlast) "AcDbDynBlockPropertyTLF2" 1)
(setpropertyvalue (entlast) "AcDbDynBlockPropertyTLF1" from_v_flip)
(command "INSERT" "TENSION_LENGTH" INSTO 1 0)
(MODIFY_ATTRIBUTES (entlast) (LIST "TENSION_LENGTH" "LOCATION_NUM" "CHAINAGE") (LIST (RTOS TL 2 2) FROM_LOC FROM_CH))
(setpropertyvalue (entlast) "rotation" to_ROT)
(setpropertyvalue (entlast) "AcDbDynBlockPropertyTLF2" 0)
(setpropertyvalue (entlast) "AcDbDynBlockPropertyTLF1" to_v_flip)
)
)
)
)
(defun C:GET_TRACK_INFO () ;TO STORE THE DATA OF DN LINE
(command "-layer" "THAW" "OHE-CIV-DFCC TRACK CENTRE LINE" "")
(setq TRACK (car (entsel "Select DN LINE")))
(setq UP_TRACK (CAR (ENTSEL "SELECT UP LINE")))
(setq KM_STONE (entsel "Select FIRST DFCC KM Stone :"))
(setq CTNKM_STONE (entsel "Select FIRST CTN KM Stone :"))
(setq BIG_Rectangle (ENTSEL "SELECT THE RECTANGLE COVERING WHOLE YARD: "))
;(command "-layer" "FREEZE" "OHE-CIV-DFCC TRACK CENTRE LINE" "")
)
(defun C:SPAN_MANUAL () ;;;;;;;;;;;;;;;;;;;;;;;;;;;;;;;;;;;;;;;;;;;;;;;;;;;;;;;;;;;;;;;;;;;;;;;;;;;;;;;TO UPDATE THE SPAN, MANUALLY BY SELECTING BLOCKS
(WHILE (> 1 0)
(setq BLOCK1 (entsel "Select BLOCK 1 : "))
(setq BLOCK2 (entsel "Select BLOCK 2 : "))
(setq BLOCK1_CORD (list (getpropertyvalue (car BLOCK1) "Position/X") (getpropertyvalue (car BLOCK1) "Position/Y") 0.0))
(setq BLOCK2_CORD (list (getpropertyvalue (car BLOCK2) "Position/X") (getpropertyvalue (car BLOCK2) "Position/Y") 0.0))
(setq BLOCK1_PROJ (vlax-curve-getClosestPointTo TRACK BLOCK1_CORD T))
(setq BLOCK2_PROJ (vlax-curve-getClosestPointTo TRACK BLOCK2_CORD T))
(setq BLOCK1_DIST (vlax-curve-getDistAtPoint TRACK BLOCK1_PROJ))
(setq BLOCK2_DIST (vlax-curve-getDistAtPoint TRACK BLOCK2_PROJ))
(setq SPAN (- BLOCK2_DIST BLOCK1_DIST))
(MODIFY_ATTRIBUTES (car BLOCK1) (LIST "SPAN1") (LIST (RTOS (ROUND SPAN 4.5) 2 2)))
)
)
(defun OBJECT_CORDINATES (OBJECT) ; To extract the cordinates of the block
(setq OBJ_CORD (list (getpropertyvalue (car OBJECT) "Position/X") (getpropertyvalue (car OBJECT) "Position/Y") 0.0))
)
(defun YARD_MAST_DATA (WPT1 WPT2 WPT3 WPT4) ; TO GET THE LISTS OF DIFFERENT MASTS IN YARD
(setq BLOCKS_LIST (SSGET "WP" (LIST WPT1 WPT2 WPT3 WPT4) (LIST (CONS 0 "INSERT"))))
(setq PORTAL_LIST (GET_BLOCK_LIST "PORTAL"))
(setq SINGLE_CANT_MAST_LIST (GET_BLOCK_LIST "SINGLE_CANT_MAST"))
(setq DOUBLE_CANT_MAST_LIST (GET_BLOCK_LIST "DOUBLE_CANT_MAST"))
(setq TRIPLE_CANT_MAST_LIST (GET_BLOCK_LIST "TRIPLE_CANT_MAST"))
(setq SINGLE_CANT_DA_LIST (GET_BLOCK_LIST "SINGLE_CANT_DA"))
(setq DOUBLE_CANT_DA_LIST (GET_BLOCK_LIST "DOUBLE_CANT_DA"))
(setq TRIPLE_CANT_DA_LIST (GET_BLOCK_LIST "TRIPLE_CANT_DA"))
(setq SINGLE_CANT_UR_LIST (GET_BLOCK_LIST "SINGLE_CANT_UPRIGHT"))
(setq DOUBLE_CANT_UR_LIST (GET_BLOCK_LIST "DOUBLE_CANT_UPRIGHT"))
(setq TRIPLE_CANT_UR_LIST (GET_BLOCK_LIST "TRIPLE_CANT_UPRIGHT"))
(setq SS0_LIST (GET_BLOCK_LIST "SS0"))
(setq TTC_LIST (GET_BLOCK_LIST "TTC"))
(setq SIGNAL_LIST1 (GET_BLOCK_LIST "SIGNAL_NEW"))
(setq SIGNAL_LIST2 (GET_BLOCK_LIST "HYBRID_SIGNAL4"))
(setq REPRESENTATION_LIST (GET_BLOCK_LIST "REPRESENTATION1"))
(setq CURVE_SUMBOL_LIST (GET_BLOCK_LIST "CURVE_SYMBOL1"))
(setq G_POST_LIST (GET_BLOCK_LIST "GRADIENT_POST"))
(setq SHUNT_SIGNAL_LIST (GET_BLOCK_LIST "SHUNT_SIGNAL"))
(setq MAST_LIST (APPEND PORTAL_LIST SINGLE_CANT_MAST_LIST DOUBLE_CANT_MAST_LIST TRIPLE_CANT_MAST_LIST SS0_LIST TTC_LIST SIGNAL_LIST1 SIGNAL_LIST2 REPRESENTATION_LIST CURVE_SUMBOL_LIST G_POST_LIST SHUNT_SIGNAL_LIST))
)

(defun C:UPDATE_FDN_CORDINATES () ;TO UPDATE THE ACTUAL CORDINATES THAT WE FILL IN CSD
(setq MODE (GETSTRING "ENTER MODE OF OPERATION : MANUAL->M | AUTOMATIC->A"))
(IF (= MODE "A")
(PROGN
(setq WPT1 (GETPOINT "\n PICK POINT1"))
(setq WPT2 (GETPOINT "\n PICK POINT2"))
(setq WPT3 (GETPOINT "\n PICK POINT3"))
(setq WPT4 (GETPOINT "\n PICK POINT4"))
(YARD_MAST_DATA WPT1 WPT2 WPT3 WPT4)
(setq CANT_MASTS_LIST (APPEND SINGLE_CANT_MAST_LIST DOUBLE_CANT_MAST_LIST TRIPLE_CANT_MAST_LIST TTC_LIST))
)
(PROGN
(setq BLOCK (entsel "Select the BLOCK : "))
(setq BLOCK_NAME (getpropertyvalue (car BLOCK) "BlockTableRecord/Name"))
(IF (OR (= BLOCK_NAME "TRIPLE_CANT_MAST") (= BLOCK_NAME "DOUBLE_CANT_MAST") (= BLOCK_NAME "SINGLE_CANT_MAST") (= BLOCK_NAME "TTC"))
(PROGN
(setq CANT_MASTS_LIST block)
(setq PORTAL_LIST NIL)
(setq SS0_LIST NIL)
)
)
(IF(= BLOCK_NAME "PORTAL")
(PROGN
(setq PORTAL_LIST block)
(setq SS0_LIST NIL)
(setq CANT_MASTS_LIST NIL)
)
)
(IF(= BLOCK_NAME "SS0")
(PROGN
(setq SS0_LIST block)
(setq CANT_MASTS_LIST NIL)
(setq PORTAL_LIST NIL)
)
)
)
)

(setq I 0)
(WHILE (< I (LENGTH CANT_MASTS_LIST))
(setq BLOCK (LIST (NTH I CANT_MASTS_LIST)))
(setq BLOCK_CORD (OBJECT_CORDINATES BLOCK))
(setq FLIP (getpropertyvalue (car BLOCK) "AcDbDynBlockPropertySTF1"))
(setq ROT (/ (* (getpropertyvalue (car BLOCK) "Rotation") 180) pi))
(setq ANG (+ (- (* (- 1 FLIP) 180) 90) ROT))
(setq FDN_CORD (POLAR BLOCK_CORD (/ (* ANG pi) 180) 0.2))
(command "POINT" fdn_cord)
(MODIFY_ATTRIBUTES (car BLOCK) (LIST "DUMMY_VARIABLE1") (LIST (STRCAT "(" (RTOS (CAR FDN_CORD) 2 2) " , " (RTOS (NTH 1 FDN_CORD) 2 2) ")")))
(setq I (+ 1 I))
)
(setq I 0)
(WHILE (< I (LENGTH PORTAL_LIST))
(setq BLOCK (LIST (NTH I PORTAL_LIST)))
(setq PORTAL_TYPE (SUBSTR (GETPROPERTYVALUE (CAR BLOCK) "MAST_TYPE1") 1 2))
(IF (= PORTAL_TYPE "WN")
(PROGN
(setq UR_W 0.275)
)(setq UR_W 0.3)
)
(setq CS_PORTAL (round (getpropertyvalue (car BLOCK) "AcDbDynBlockPropertySTL1") 0.05))
(setq BLOCK_CORD (OBJECT_CORDINATES BLOCK))
(setq ROT (/ (* (getpropertyvalue (car BLOCK) "Rotation") 180) pi))
(setq ANG1 (+ 270 ROT))
(setq ANG2 (+ 90 ROT))
(setq FDN_CORD1 (POLAR BLOCK_CORD (/ (* ANG1 pi) 180) UR_W))
(setq FDN_CORD2 (POLAR BLOCK_CORD (/ (* ANG2 pi) 180) (+ UR_W CS_PORTAL)))
(command "POINT" fdn_cord1)
(command "POINT" fdn_cord2)
(MODIFY_ATTRIBUTES (car BLOCK) (LIST "DUMMY_VARIABLE5" "DUMMY_VARIABLE1") (LIST (STRCAT "(" (RTOS (CAR FDN_CORD1) 2 2) " , " (RTOS (NTH 1 FDN_CORD1) 2 2) ")") (STRCAT "(" (RTOS (CAR FDN_CORD2) 2 2) " , " (RTOS (NTH 1 FDN_CORD2) 2 2) ")")))
(setq I (+ 1 I))
)
(setq p 0)
(while (< p (/ (length SS0_LIST) 2))
(setq BLOCK (LIST (NTH p SS0_LIST)))
(setq block_cord_ss0 (OBJECT_CORDINATES block))
(setq ss0_x (nth 0 block_cord_ss0))
(setq ss0_y (nth 1 block_cord_ss0))
(command "POINT" block_cord_ss0)
(MODIFY_ATTRIBUTES (car BLOCK) (LIST "DUMMY_VARIABLE1") (LIST (STRCAT "(" (RTOS SS0_X 2 2) ", " (RTOS SS0_Y 2 2) ")" )))
(setq P (+ 1 P))
)
(IF (= MODE "A")
(PROGN
(COMMAND "" "M" "")
)
)
)
(defun GET_BLOCK_LIST (NAME / I) ;; TO EXTRACT A PARTICULAR BLOCK NAME LIKE 'PORTALS' ONLY FROM ALL BLOCKS LIST
(setq BL_NAME NAME)
(setq I 0)
(setq BLOCK_LIST NIL)
(WHILE (< I (sslength BLOCKS_LIST))
(setq BLOCK_NAME (VLAX-GET-PROPERTY (VLAX-ENAME->VLA-OBJECT (SSNAME BLOCKS_LIST I)) 'EFFECTIVENAME))
(IF (= BLOCK_NAME BL_NAME)
	(PROGN
		(setq BLOCK_LIST (APPEND BLOCK_LIST (LIST (SSNAME BLOCKS_LIST I))))
	)
	)
	(setq I (+ 1 I))
	BLOCK_LIST
)
)
(defun C:CORDINATES_OPENROUTE () ; To correct Cordinates in openroute
(setq WPT1 (GETPOINT "\n PICK POINT1"))
(setq WPT2 (GETPOINT "\n PICK POINT2"))
(setq WPT3 (GETPOINT "\n PICK POINT3"))
(setq WPT4 (GETPOINT "\n PICK POINT4"))
(YARD_MAST_DATA WPT1 WPT2 WPT3 WPT4)
(setq CANT_MASTS_LIST (APPEND SINGLE_CANT_MAST_LIST DOUBLE_CANT_MAST_LIST))
(setq I 0)
(while (< I (length CANT_MASTS_LIST))
(setq BLOCK (LIST (NTH I CANT_MASTS_LIST)))
;(setq BLOCK (ENTSEL "SELECT MAST"))
(setq BLOCK_CORD (OBJECT_CORDINATES BLOCK))
(setq FLIP (getpropertyvalue (car BLOCK) "AcDbDynBlockPropertySTF1"))
(setq IMPLANTATION (getpropertyvalue (car BLOCK) "AcDbDynBlockPropertySTL1"))
(setq ROT (/ (* (getpropertyvalue (car BLOCK) "Rotation") 180) pi))
(setq ANG (+ (- (* FLIP 180) 90) ROT))
(setq FDN_CORD (POLAR BLOCK_CORD (/ (* ANG pi) 180) IMPLANTATION))
(command "POINT" fdn_cord)
(MODIFY_ATTRIBUTES (car BLOCK) (LIST "DUMMY_VARIABLE11") (LIST (STRCAT "(" (RTOS (CAR FDN_CORD) 2 2) " , " (RTOS (NTH 1 FDN_CORD) 2 2) ")") ))
(Setpropertyvalue (car BLOCK) "color" "3")
(setq I (+ 1 I))
)
)
(defun C:CORDINATES_OPENROUTE_DN() ; To correct Cordinates in openroute
(while (> 1 0)
(setq BLOCK (ENTSEL "SELECT MAST"))
(setq BLOCK_CORD (OBJECT_CORDINATES BLOCK))
(setq BLOCK_CORD_PROJ (vlax-curve-getClosestPointTo TRACK BLOCK_CORD T))
(MODIFY_ATTRIBUTES (car BLOCK) (LIST "DUMMY_VARIABLE1") (LIST (STRCAT "(" (RTOS (CAR BLOCK_CORD_PROJ) 2 2) " , " (RTOS (NTH 1 BLOCK_CORD_PROJ) 2 2) ")") ))
)
)
(defun C:CORDINATES_OPENROUTE_UP() ; To correct Cordinates in openroute
(while (> 1 0)
(setq BLOCK (ENTSEL "SELECT MAST"))
(setq BLOCK_CORD (OBJECT_CORDINATES BLOCK))
(COMMAND "POINT" BLOCK_CORD)
(setq BLOCK_CORD_PROJ (vlax-curve-getClosestPointTo UP_TRACK BLOCK_CORD T))
(COMMAND "POINT" BLOCK_CORD_PROJ)
(MODIFY_ATTRIBUTES (car BLOCK) (LIST "DUMMY_VARIABLE1") (LIST (STRCAT "(" (RTOS (CAR BLOCK_CORD_PROJ) 2 2) " , " (RTOS (NTH 1 BLOCK_CORD_PROJ) 2 2) ")") ))
)
)
(defun POLYLINE_POINTS (PLINE / I LST) ; Get the list of Polyline points from left to right
(setq PL_PTS nil)
(setq i 0)
(setq lst (entget (CAR PLINE)))
(repeat (length lst)
(if (= (car (nth i lst)) 10)
(setq PL_PTS (append PL_PTS (list (cdr (nth i lst)))))
)
(setq i (1+ i))
)
PL_PTS
)
(defun C:ACC (/) ; colors the wires which require ACC
(WHILE (> 1 0)
(SETQ WIRE (ENTSEL))
(SETQ FIRST_PT (NTH 0 (POLYLINE_POINTS WIRE)))
(SETQ LAST_PT (LAST (POLYLINE_POINTS WIRE)))
(setq FIRST_PT_PROJ (vlax-curve-getClosestPointTo TRACK FIRST_PT T))
(setq LAST_PT_PROJ (vlax-curve-getClosestPointTo TRACK LAST_PT T))
(setq FIRST_PT_DIST (vlax-curve-getDistAtPoint TRACK FIRST_PT_PROJ))
(setq LAST_PT_DIST (vlax-curve-getDistAtPoint TRACK LAST_PT_PROJ))
(SETQ TL (- LAST_PT_DIST FIRST_PT_DIST))
(IF (> TL 750)
(PROGN
(setpropertyvalue (CAR WIRE) "Color" "4")
)
)
)
)
(defun C:INPUT_TRACK_DATA ( / TRACK_SET TEMP_VAR_TRACK TEMP_VAR_TRACKNAME) ; Store the track entities corresponding to their Yard names
(setq TRACKS_LIST NIL)
(WHILE (> 1 0)
(setq TEMP_VAR_TRACK (CAR(ENTSEL "SELECT TRACK")))
(setq TEMP_VAR_TRACKNAME (GETSTRING "ENTER THE TRACK NAME : "))
(setq TRACK_SET (CONS TEMP_VAR_TRACK TEMP_VAR_TRACKNAME))
(setq TRACK_LIST (APPEND TRACK_LIST (LIST TEMP_VAR_TRACK)))
(setq TRACK_NAMES_LIST (APPEND TRACK_NAMES_LIST (TRACK_SET)))
)
)
(defun WHICH_TRACK (WIRE_PT) ; Returns the the track on which the wire is.
(setq PT WIRE_PT)
(setq I 0)
(setq TRACK_TEMP_PER_DIST 0)
(setq TRACK_PER_DIST 0)
(setq NEAREST_TRACK NIL)
(REPEAT (LENGTH TRACK_LIST)
(setq TRACK_PT (vlax-curve-getClosestPointTo (NTH I TRACK_LIST) PT T))
(setq TRACK_TEMP_PER_DIST (SQRT (+ (* (- (NTH 0 PT) (NTH 0 TRACK_PT)) (- (NTH 0 PT) (NTH 0 TRACK_PT))) (* (- (NTH 1 PT) (NTH 1 TRACK_PT)) (- (NTH 1 PT) (NTH 1 TRACK_PT))))))
(IF (<= TRACK_TEMP_PER_DIST TRACK_PER_DIST)
(setq TRACK_TEMP_PER_DIST TRACK_PER_DIST)
(setq NEAREST_TRACK (NTH I TRACK_LIST))
)
)
NEAREST_TRACK
)
(defun GET_PORTAL_TYPE (CS / I) ;RETURNS THE TYPE OF PORTAL FOR CS INPUT
(setq PORTAL_CS_LIST (list 11.5 11.75 12.25 12.75 13.45 13.95 14.45 14.95 15.45 15.95 16.45 16.95 17.45 14.95 18.45 18.95 19.45 19.95 20.45 20.95 21.45 21.95 22.25 22.95 23.45 23.95 24.45 24.95 25.45 25.95 26.45 26.95 27.45 27.95 28.45 28.95 29.45 29.95 30.45 30.95 31.45 31.95 32.45 32.95 33.45 33.95 34.45))
(setq PORTAL_TYPE_LIST (list "WN-1" "WN-2" "WN-3" "WN-4" "WN-5" "WN-6" "WN-7" "WN-8" "WN-9" "WN-10" "WN-11" "WN-12" "WN-13" "WN-14" "WN-15" "WN-16" "WN-17" "WN-18" "WN-19" "WN-20" "WN-21" "WO(A)-24" "WO(A)-25" "WO(A)-26" "WO(A)-27" "WO(A)-28" "WO(A)-29" "WO(A)-30" "WO(A)-31" "WO(A)-32" "WO(A)-33" "WO(A)-34" "WO(A)-35" "WO(A)-36" "WR-16" "WR-17" "WR-18" "WR-19" "WR-20" "WR-21" "WR-22" "WR-23" "WR-24" "WR-25" "WR-26" "WR-27" "WR-28" ))
(setq TYPEis nil)
(setq I 0)
(WHILE (< I 47)
(IF (>= CS (NTH I PORTAL_CS_LIST))
(PROGN
(setq TYPEis (NTH I PORTAL_TYPE_LIST))
)
)
(setq I (+ I 1))
)
TYPEis
)
(defun C:SHOW_MASTS_FOR_TRACK () ; Highlits the masts color on the selected track
;(FOREACH X MAST_LIST (setpropertyvalue X "Color" "1"))
(setq WPT1 (GETPOINT "\n PICK POINT1"))
(setq WPT2 (GETPOINT "\n PICK POINT2"))
(setq WPT3 (GETPOINT "\n PICK POINT3"))
(setq WPT4 (GETPOINT "\n PICK POINT4"))
(YARD_MAST_DATA WPT1 WPT2 WPT3 WPT4)
(setq COLOR (GETINT "ENTER INDEX OF COLOR"))
(setq MAST_LIST NIL)
(setq MAST_LIST (APPEND SINGLE_CANT_MAST_LIST (APPEND DOUBLE_CANT_MAST_LIST TRIPLE_CANT_MAST_LIST TTC_LIST SS0_LIST SINGLE_CANT_DA_LIST DOUBLE_CANT_DA_LIST TRIPLE_CANT_DA_LIST SINGLE_CANT_UR_LIST DOUBLE_CANT_UR_LIST TRIPLE_CANT_UR_LIST)))
(setq TEMP_TRACK (entsel "SELECT THE TRACK"))
(setq I 0)
(setq MAST_ONLINE NIL)
(WHILE (< I (LENGTH MAST_LIST))
(setq MAST_BLOCK (VLAX-GET-PROPERTY (VLAX-ENAME->VLA-OBJECT (NTH I MAST_LIST)) 'EFFECTIVENAME))
(setq DIST1 (DISTANCE (OBJECT_CORDINATES (LIST (NTH I MAST_LIST))) (vlax-curve-getClosestPointTo (CAR TEMP_TRACK) (OBJECT_CORDINATES (LIST (NTH I MAST_LIST))) T)))
(IF (/= MAST_BLOCK "SS0")
(PROGN
(setq ROT (/ (* (getpropertyvalue (NTH I MAST_LIST) "Rotation") 180) pi))
(setq FLIP (getpropertyvalue (NTH I MAST_LIST) "AcDbDynBlockPropertySTF1"))
(setq ANG (+ (- (* FLIP 180) 90) ROT))
(setq PT2 (POLAR (OBJECT_CORDINATES (LIST (NTH I MAST_LIST))) (/ (* ANG pi) 180) 2.5))
(setq DIST2 (DISTANCE PT2 (vlax-curve-getClosestPointTo (CAR TEMP_TRACK) PT2 T)))
)
)
(if (< DIST1 3.6)
(PROGN
(IF (/= MAST_BLOCK "SS0")
(PROGN
(IF (> DIST1 DIST2)
(setq MAST_ONLINE (APPEND MAST_ONLINE (LIST (NTH I MAST_LIST))))
)
)
(PROGN
(setq MAST_ONLINE (APPEND MAST_ONLINE (LIST (NTH I MAST_LIST))))
)
)
)
)
(setq I (+ 1 I))
)
(FOREACH X MAST_ONLINE (setpropertyvalue X "Color" (RTOS COLOR 2 0)))
)
(defun SORT_FUN	(LIST1 FLAG1 FLAG2 /)
  (IF (= NIL (VL-CONSP (CAR LIST1)))
    (PROGN (setq LIST1 (INDEX_ADD LIST1))
	   (setq LIST1
		  (VL-SORT LIST1
			   '(LAMBDA (X Y) (< (CADR X) (CADR Y)))
		  )
	   )
	   (setq LIST1 (MAPCAR '(LAMBDA (X) (CADR X)) LIST1))
    )
    (PROGN
      (IF (NOT (ATOM (NTH FLAG1 (NTH 0 LIST1))))
	(setq LIST1
	       (VL-SORT
		 LIST1
		 '(LAMBDA (X Y)
		    (< (NTH FLAG2 (NTH FLAG1 X)) (NTH FLAG2 (NTH FLAG1 Y)))
		  )
	       )
	)
	(PROGN (setq LIST1
		      (VL-SORT LIST1
			       '(LAMBDA (X Y) (< (NTH FLAG2 X) (NTH FLAG2 Y)))
		      )
	       )
	)
      )
    )
  )
  LIST1
)
(defun GET_ATTRIBUTE_VALUE (attribname entname)
(SETQ Attribval (NTH 1 (ASSOC ATTRIBNAME (GET_ATTRIBUTES ENTNAME))))
ATTRIBVAL
)
(defun GET_ATTRIBUTES (ENTNAME / ENT_OBJECT SAFEARRAY_SET I LIST1) ; gets the value of attribute stored in a block
  (setq SAFEARRAY_SET NIL)
  (setq ENT_OBJECT ENTNAME)
  (setq ENT_OBJECT (VLAX-ENAME->VLA-OBJECT ENT_OBJECT))
  (IF (= (VLAX-GET-PROPERTY ENT_OBJECT "HASATTRIBUTES")
	 :VLAX-TRUE
      )
    (PROGN
      (setq SAFEARRAY_SET
	     (VLAX-SAFEARRAY->LIST
	       (VLAX-VARIANT-VALUE
		 (VLAX-INVOKE-METHOD ENT_OBJECT "GETATTRIBUTES")
	       )
	     )
      )

      (setq I 0)
      (setq LIST1 NIL)
      (WHILE (< I (LENGTH SAFEARRAY_SET))
	(setq
	  LIST1	(CONS
		  (LIST
		    (VLAX-GET-PROPERTY
		      (NTH I SAFEARRAY_SET)
		      "TAGSTRING"
		    )
		    (VLAX-GET-PROPERTY
		      (NTH I SAFEARRAY_SET)
		      "TEXTSTRING"
		    )
		    ;(VLAX-SAFEARRAY->LIST
		    ;  (VLAX-VARIANT-VALUE
			;(VLAX-GET-PROPERTY
			;  (NTH I SAFEARRAY_SET)
			;  "InsertionPoint"
			;)
		    ;  )
		    ;)
		    ;(IF	(= (VLAX-GET-PROPERTY
			;     (NTH I SAFEARRAY_SET)
			;     'VISIBLE
			;   )
			;   :VLAX-TRUE
			;)
		    ;  1
		    ;  0
		    ;)
		  )
		  LIST1
		)
	)
	(setq I (+ I 1))
      )
      (setq LIST1 (REVERSE LIST1))
      (setq LIST1 (SORT_FUN LIST1 0 0))
    )
    (setq LIST1 NIL)
  )
  LIST1

)
(defun MODIFY_ATTRIBUTES (ENTNAME     IDENTIFIER  VALUE ; enters the value of an attribute
			  /	      TEMP_ELE	  ENT_OBJECT
			  SAFEARRAY_SET		  I
			  J
			 )
  (setq SAFEARRAY_SET NIL)
  (setq ENT_OBJECT ENTNAME)
  (setq ENT_OBJECT (VLAX-ENAME->VLA-OBJECT ENT_OBJECT))
  (IF (= (VLAX-GET-PROPERTY ENT_OBJECT "HASATTRIBUTES")
	 :VLAX-TRUE
      )
    (PROGN
      (setq SAFEARRAY_SET
	     (VLAX-SAFEARRAY->LIST
	       (VLAX-VARIANT-VALUE
		 (VLAX-INVOKE-METHOD ENT_OBJECT "GETATTRIBUTES")
	       )
	     )
      )

      (setq I 0)
      (setq J 0)
      (setq LIST1 NIL)
      (WHILE (< I (LENGTH SAFEARRAY_SET))
	(setq TEMP_ELE
	       (VLAX-GET-PROPERTY (NTH I SAFEARRAY_SET) "TAGSTRING")
	)
	(IF (/= (VL-POSITION TEMP_ELE IDENTIFIER) NIL)
	  (PROGN (VLAX-PUT-PROPERTY
		   (NTH I SAFEARRAY_SET)
		   "TEXTSTRING"
		   (NTH (VL-POSITION TEMP_ELE IDENTIFIER) VALUE)
		 )
	  )
	)
	(setq I (+ I 1))
      )
    )
  )
)
(defun RenAttrib ($blk $old $new / blocks bo eo ao) ; renames the attribute in a block allover the drawing
  ;; Get blocks collection in current drawing
  (setq blocks (vla-get-Blocks (vla-get-ActiveDocument (vlax-get-acad-object))))
  ;; Step through all blocks
  (vlax-for bo blocks
    ;; Step through all entities inside block
    (vlax-for eo bo
      (cond
        ;; If attdef & in target block & old tag
        ((and (= (vla-get-ObjectName eo) "AcDbAttributeDefinition")
              (= (strcase (vla-get-Name bo)) (strcase $blk))
              (= (vla-get-TagString eo) $old)
         ) ;_ end of and
         (vla-put-TagString eo $new) ;Change to new name
        )
        
        ;; If block reference & target block
        ((and (= (vla-get-ObjectName eo) "AcDbBlockReference")
              (= (strcase (vla-get-EffectiveName eo)) (strcase $blk))
         ) ;_ end of and
         ;; Step through all attributes
         (foreach ao (vlax-safearray->list (vlax-variant-value (vla-GetAttributes eo)))
           ;; Check if target attrib
           (if (= (strcase (vla-get-TagString ao)) (strcase $old))
             (vla-put-TagString ao $new) ;Change to new name
           ) ;_ end of if
         ) ;_ end of foreach
        )
      ) ;_ end of cond
    ) ;_ end of vlax-for
  ) ;_ end of vlax-for
) ;_ end of defun

(defun FILL_CAD_TABLE (ENTNAME COL_NO ROW_NO LIST1 FLAG / I)
  (setq I 0)
  (IF (= FLAG "C")

    (PROGN
      (WHILE (< I (LENGTH LIST1))
	(VLAX-INVOKE-METHOD
	  (VLAX-ENAME->VLA-OBJECT ENTNAME)
	  "SETCELLVALUE"
	  ROW_NO
	  COL_NO
	  (NTH I LIST1)
	)
	(setq ROW_NO (+ ROW_NO 1))
	(setq I (+ I 1))
      )
    )

    (PROGN
      (WHILE (< I (LENGTH LIST1))
	(VLAX-INVOKE-METHOD
	  (VLAX-ENAME->VLA-OBJECT ENTNAME)
	  "SETCELLVALUE"
	  ROW_NO
	  COL_NO
	  (NTH I LIST1)
	)
	(setq COL_NO (+ COL_NO 1))
	(setq I (+ I 1))
      )
    )
  )

)
(DEFUN C:LOAD_HRL ( / ) ; loads the HRL excel sheet
  (OPENEXCEL (FINDFILE (GETFILED "SELECT HRL FILE" "" "" 8)) "HRL" T)
)
(DEFUN C:PRINT_HRL ( / ) ; Prints the HRL in the masts
(SETQ START_CELL (GETSTRING "\N ENTER STARTING CELL"))
(SETQ END_CELL (GETSTRING "\N ENTER ENDING CELL"))
(setq MODE (GETSTRING "ENTER MODE OF OPERATION : MANUAL->M | AUTOMATIC->A"))
(IF (= MODE "A")
(PROGN
(setq WPT1 (GETPOINT "\n PICK POINT1"))
(setq WPT2 (GETPOINT "\n PICK POINT2"))
(setq WPT3 (GETPOINT "\n PICK POINT3"))
(setq WPT4 (GETPOINT "\n PICK POINT4"))
(YARD_MAST_DATA WPT1 WPT2 WPT3 WPT4)
(setq BLOCK_LIST MAST_LIST)
))
(setq BLOCK_LIST MAST_LIST)
(SETQ CHAINAGE_LIST (getCellsrow/column "HRL" (STRCAT (COLUMN+N START_CELL 0) ":" (COLUMN+N END_CELL 0))))
(SETQ HRL_LIST (getCellsrow/column "HRL" (STRCAT (COLUMN+N START_CELL 1) ":" (COLUMN+N END_CELL 1))))
(SETQ I 0)
(WHILE (IF (= MODE "M") (PROGN (> 1 0))(PROGN (< I (LENGTH BLOCK_LIST))))
(IF (= MODE "M")
(PROGN
(setq BLOCK (entsel "Select the BLOCK : "))
)
)
(IF (= MODE "A")
(PROGN
(setq BLOCK (LIST (NTH I BLOCK_LIST)))
)
)
(setq BLOCK_NAME (getpropertyvalue (CAR BLOCK) "BlockTableRecord/Name"))
(IF(= BLOCK_NAME "PORTAL")
(PROGN
(SETQ BLOCK_CHAIN (NTH 1 (ASSOC "CHAINAGE3" (GET_ATTRIBUTES (CAR BLOCK)))))
(SETQ SLASH_LOC (vl-string-search "/" BLOCK_CHAIN))
(SETQ STR1 (SUBSTR BLOCK_CHAIN 1 SLASH_LOC))
(SETQ STR2 (SUBSTR BLOCK_CHAIN (+ 2 SLASH_LOC)))
(WHILE (< (STRLEN STR2) 6)
(PROGN
(SETQ STR2 (STRCAT "0" STR2))
)
)
(SETQ CH (ATOF (STRCAT (STRCAT STR1 STR2))))
)
)
(IF(OR (= BLOCK_NAME "SS0") (= BLOCK_NAME "TRIPLE_CANT_MAST") (= BLOCK_NAME "DOUBLE_CANT_MAST") (= BLOCK_NAME "SINGLE_CANT_MAST") (= BLOCK_NAME "TTC"))
(PROGN
(SETQ BLOCK_CHAIN (NTH 1 (ASSOC "CHAINAGE2" (GET_ATTRIBUTES (CAR BLOCK)))))
(SETQ SLASH_LOC (vl-string-search "/" BLOCK_CHAIN))
(SETQ STR1 (SUBSTR BLOCK_CHAIN 1 SLASH_LOC))
(SETQ STR2 (SUBSTR BLOCK_CHAIN (+ 2 SLASH_LOC)))
(WHILE (< (STRLEN STR2) 6)
(PROGN
(SETQ STR2 (STRCAT "0" STR2))
)
)
(SETQ CH (ATOF (STRCAT (STRCAT STR1 STR2))))
)
)
(SETQ J 0)
(WHILE (< J (LENGTH CHAINAGE_LIST))
(IF (> CH (NTH J CHAINAGE_LIST))
(PROGN 
(SETQ HRL_BLOCK (NTH J HRL_LIST))
(MODIFY_ATTRIBUTES (CAR BLOCK) (LIST "DUMMY_VARIABLE2") (LIST HRL_BLOCK))
;(setpropertyvalue (CAR BLOCK) "Color" "3")
)
)
(SETQ J (+ 1 J))
)
(IF (= MODE "A")
(PROGN
(setq I (+ 1 I))
)
)
)
)
(defun GET_BLOCK_LIST (NAME / I) ;; TO EXTRACT A PARTICULAR BLOCK NAME LIKE 'PORTALS' ONLY FROM ALL BLOCKS LIST
(setq BL_NAME NAME)
(setq I 0)
(setq BLOCK_LIST NIL)
(WHILE (< I (sslength BLOCKS_LIST))
(setq BLOCK_NAME (VLAX-GET-PROPERTY (VLAX-ENAME->VLA-OBJECT (SSNAME BLOCKS_LIST I)) 'EFFECTIVENAME))
(IF (= BLOCK_NAME BL_NAME)
	(PROGN
		(setq BLOCK_LIST (APPEND BLOCK_LIST (LIST (SSNAME BLOCKS_LIST I))))
	)
	)
	(setq I (+ 1 I))
	BLOCK_LIST
)
)
(defun C:FILL_ANCH_DETAILS ( / I) ; FILLS ANCHORS WITH ANCHOR DETAILS
;AcDbDynBlockPropertyANF1
(princ "MAKE SURE YOU HAVE UPDATED CORDINATES")
(while (> 1 0)
(setq Rectangle (ENTSEL "SELECT THE RECTANGLE: "))
; (setq WPT1 (GETPOINT "\n PICK POINT1"))
; (setq WPT2 (GETPOINT "\n PICK POINT2"))
; (setq WPT3 (GETPOINT "\n PICK POINT3"))
; (setq WPT4 (GETPOINT "\n PICK POINT4"))
(setq WPT1 (nth 0 (POLYLINE_POINTS  RECTANGLE)))
(setq WPT2 (nth 1 (POLYLINE_POINTS  RECTANGLE)))
(setq WPT3 (nth 2 (POLYLINE_POINTS  RECTANGLE)))
(setq WPT4 (nth 3 (POLYLINE_POINTS  RECTANGLE)))
(YARD_MAST_DATA WPT1 WPT2 WPT3 WPT4)
(setq ANCHORS_LIST (GET_BLOCK_LIST "ANCHOR"))
(setq I 0)
(WHILE (< I (LENGTH ANCHORS_LIST))
(setq ANCHOR (LIST (NTH I ANCHORS_LIST)))
;(setq ANCHOR (ENTSEL))
(setq TEMP_MAST NIL)
(setq BLOCK_CORD (OBJECT_CORDINATES ANCHOR))
(setq ROT (/ (* (getpropertyvalue (car ANCHOR) "Rotation") 180) pi))
(setq ANG1 (+ ROT 135))
(setq ANG2 (+ ROT 315))
(setq PT1 (POLAR BLOCK_CORD (/ (* ANG1 pi) 180) 0.5))
(setq PT2 (POLAR BLOCK_CORD (/ (* ANG2 pi) 180) 0.5))
(setq BLOCKS_LIST (SSGET "_C" PT1 PT2 (LIST (CONS 0 "INSERT"))))
(setq LIST_TO_SEARCH (LIST "PORTAL" "SINGLE_CANT_MAST" "DOUBLE_CANT_MAST" "TRIPLE_CANT_MAST" "SS0" "TTC"))
(setq J 0)
(WHILE (= TEMP_MAST NIL)
(setq TEMP_MAST (GET_BLOCK_LIST (NTH J LIST_TO_SEARCH)))
(setq J (+ J 1))
)
(setq MAST_BLOCK (VLAX-GET-PROPERTY (VLAX-ENAME->VLA-OBJECT (NTH 0 TEMP_MAST)) 'EFFECTIVENAME))
	(IF (= MAST_BLOCK "PORTAL")
		(PROGN
		(Setq MAST_CORD1 (LIST (nth 0 (READ (NTH 1 (ASSOC "DUMMY_VARIABLE1" (GET_ATTRIBUTES (NTH 0 TEMP_MAST)))))) (nth 2 (READ (NTH 1 (ASSOC "DUMMY_VARIABLE1" (GET_ATTRIBUTES (NTH 0 TEMP_MAST)))))) 0.0))
		(Setq MAST_CORD2 (LIST (nth 0 (READ (NTH 1 (ASSOC "DUMMY_VARIABLE5" (GET_ATTRIBUTES (NTH 0 TEMP_MAST)))))) (nth 2 (READ (NTH 1 (ASSOC "DUMMY_VARIABLE5" (GET_ATTRIBUTES (NTH 0 TEMP_MAST)))))) 0.0))
		(setq ANC_CORD (OBJECT_CORDINATES ANCHOR))
		(SETQ DIST_L (DISTANCE ANC_CORD MAST_CORD1))
		(SETQ DIST_R (DISTANCE ANC_CORD MAST_CORD2))
		(IF (> DIST_L DIST_R)
			(PROGN
			(setq TEMP_MAST_NUMBER (NTH 1 (ASSOC "MAST_NUMBER2" (GET_ATTRIBUTES (NTH 0 TEMP_MAST)))))
			(setq TEMP_MAST_CHAINAGE (NTH 1 (ASSOC "CHAINAGE2" (GET_ATTRIBUTES (NTH 0 TEMP_MAST)))))
			)
			(PROGN
			(setq TEMP_MAST_NUMBER (NTH 1 (ASSOC "MAST_NUMBER1" (GET_ATTRIBUTES (NTH 0 TEMP_MAST)))))
			(setq TEMP_MAST_CHAINAGE (NTH 1 (ASSOC "CHAINAGE1" (GET_ATTRIBUTES (NTH 0 TEMP_MAST)))))
			)
		)
		)
		(PROGN
		(setq TEMP_MAST_NUMBER (NTH 1 (ASSOC "MAST_NUMBER1" (GET_ATTRIBUTES (NTH 0 TEMP_MAST)))))
		(setq TEMP_MAST_CHAINAGE (NTH 1 (ASSOC "CHAINAGE1" (GET_ATTRIBUTES (NTH 0 TEMP_MAST)))))
		)
	)
(MODIFY_ATTRIBUTES (CAR ANCHOR) (LIST "ANCHOR_MAST_NO" "ANCHOR_CHAINAGE") (LIST TEMP_MAST_NUMBER TEMP_MAST_CHAINAGE))
(setq I (+ I 1))
)
)
)
(defun C:Schematic_xlines ( / ST_WIRE END_WIRE ST_PT END_PT ST_PROJ END_PROJ ST_DIST END_DIST ST_OFF END_OFF)
(if (= TRACK NIL)
(progn
(alert "Track tho select kar Biyani!")
)
)
(setq KM_STONE_CORD (list (getpropertyvalue (car KM_STONE) "Position/X") (getpropertyvalue (car KM_STONE) "Position/Y") 0.0))
(setq KM_STONE_PROJ (vlax-curve-getClosestPointTo TRACK KM_STONE_CORD T))
(setq KM_DIST (vlax-curve-getDistAtPoint TRACK KM_STONE_PROJ))
;(setq BLOCK_PROJ (vlax-curve-getClosestPointTo TRACK BLOCK_CORD T))
;(setq BLOCK_DIST (vlax-curve-getDistAtPoint TRACK BLOCK_PROJ))
;(setq Off_line (entsel "Select Xline for offset : "))
(setq st_wire (entsel "Select Starting of Wire : "))
(setq end_wire (car (entsel "Select Ending of Wire : ")))
(setq St_pt (nth 0 (POLYLINE_POINTS st_wire)))
(setq end_pt (last (POLYLINE_POINTS st_wire)))
(setq st_proj (vlax-curve-getClosestPointTo TRACK St_pt T))
(setq end_proj (vlax-curve-getClosestPointTo TRACK end_pt T))
(setq st_dist (vlax-curve-getDistAtPoint TRACK st_proj))
(setq end_dist (vlax-curve-getDistAtPoint TRACK end_proj))
(setq st_off (/ (- st_dist KM_DIST) 4))
(setq end_off (/ (- end_dist KM_DIST) 4))
(command "OFFSET" st_off Off_line KM_STONE_CORD "")
(command "OFFSET" end_off Off_line KM_STONE_CORD "")
)
(defun C:Mark_block ( / SAMPLE_BLOCK_NAME SAMPLE_BLOCKS_LIST WPT1 WPT2 WPT3 WPT4 I SAMPLE_BLOCK_CORD SAMPLE_BLOCK_CORD_PROJ)
(setq SAMPLE_BLOCK_NAME (GETSTRING "ENTER THE BLOCK NAME"))
(setq WPT1 (GETPOINT "\n PICK POINT1"))
(setq WPT2 (GETPOINT "\n PICK POINT2"))
(setq WPT3 (GETPOINT "\n PICK POINT3"))
(setq WPT4 (GETPOINT "\n PICK POINT4"))
(YARD_MAST_DATA WPT1 WPT2 WPT3 WPT4)
(setq SAMPLE_BLOCKS_LIST (GET_BLOCK_LIST SAMPLE_BLOCK_NAME))
(SETQ I 0)
(WHILE (< I (LENGTH SAMPLE_BLOCKS_LIST))
(SETQ SAMPLE_BLOCK (NTH I SAMPLE_BLOCKS_LIST))
(setq SAMPLE_BLOCK_CORD (OBJECT_CORDINATES (LIST SAMPLE_BLOCK)))
(SETQ SAMPLE_BLOCK_CORD_PROJ (vlax-curve-getClosestPointTo TRACK SAMPLE_BLOCK_CORD T))
(COMMAND "XLINE" SAMPLE_BLOCK_CORD SAMPLE_BLOCK_CORD_PROJ "")
(SETQ I (+ 1 I))
)
)
(defun C:LSW ( / ST_WIRE END_WIRE ST_PT END_PT ST_PROJ END_PROJ ST_DIST END_DIST ST_OFF END_OFF)
(setq st_wire (entsel "Select Starting of Wire : "))
(setq end_wire (car (entsel "Select Ending of Wire : ")))
(setq St_pt (nth 0 (POLYLINE_POINTS st_wire)))
(setq end_pt (last (POLYLINE_POINTS st_wire)))
(setq st_proj (vlax-curve-getClosestPointTo TRACK St_pt T))
(setq end_proj (vlax-curve-getClosestPointTo TRACK end_pt T))
(setq st_dist (vlax-curve-getDistAtPoint TRACK st_proj))
(setq end_dist (vlax-curve-getDistAtPoint TRACK end_proj))
(setq LSW_L (- end_dist st_dist))
(ALERT (STRCAT "THE LSW LENGTH IS " (RTOS (ABS LSW_L) 2 2)))
)

(defun c:TS (/ LIST1 FLAG)
  (vl-load-com)
  (SETQ  FLAG "1")
  (SETQ FLAG1 "E")
  (IF (= FLAG1 "S")
   (SETQ ATTR_TAG (CDR (ASSOC 2 (ENTGET (CAR (NENTSEL "SELECT ATTRIBUTE"))))))
   (SETQ ATTR_TAG "TS")
   )
  (SETQ LIST1 (SSGET))
  (SETQ LIST1 (FORM_SSSET LIST1))
  (SETQ I 0)
  (while (< I (LENGTH LIST1))
      (CHANGE_VISIBILITY (NTH I LIST1) (LIST ATTR_TAG) (LIST FLAG))
      (SETQ  I (+ I 1)))
  (princ))

(defun c:q () ; Turns on the Snap
	
	(setvar "osmode" 16383)
	(setvar "blipmode" 0)
)
(defun c:vis_attrib (/ LIST1 FLAG)
  (vl-load-com)
  (SETQ  FLAG "1")
  (SETQ FLAG1 "E")
  (IF (= FLAG1 "S")
   (SETQ ATTR_TAG (CDR (ASSOC 2 (ENTGET (CAR (NENTSEL "SELECT ATTRIBUTE"))))))
   (SETQ ATTR_TAG (GETSTRING "/N ENTER TAGNAME : ")))
  (SETQ LIST1 (SSGET))
  (SETQ LIST1 (FORM_SSSET LIST1))
  (SETQ I 0)
  (while (< I (LENGTH LIST1))
      (CHANGE_VISIBILITY (NTH I LIST1) (LIST ATTR_TAG) (LIST FLAG))
      (SETQ  I (+ I 1)))
  (princ))
(DEFUN C:WER_DIS_ON_TRACK ( / POLYLINE_ENTITY POINT1 POINT2 TEMP_DISTANCE1 TEMP_DISTANCE2 I )

  (SETQ POLYLINE_ENTITY TRACK)
  (SETQ XLINE1_CORD (getpropertyvalue (car(entsel "SELECT XLINE1")) "BasePoint"))
  (SETQ XLINE2_CORD (getpropertyvalue (CAR(ENTSEL "SELECT XLINE2")) "BasePoint"))
  (SETQ POINT1 (vlax-curve-getClosestPointTo TRACK XLINE1_CORD T))
  (SETQ POINT2 (vlax-curve-getClosestPointTo TRACK XLINE2_CORD T))
  (SETQ TEMP_DISTANCE1 (VLAX-CURVE-GETDISTATPOINT POLYLINE_ENTITY POINT1))
  (SETQ TEMP_DISTANCE2 (VLAX-CURVE-GETDISTATPOINT POLYLINE_ENTITY POINT2))
  (ALERT (STRCAT "THE DISTANCE IS " (RTOS (ABS (- TEMP_DISTANCE1 TEMP_DISTANCE2)) 2 2)))

)
(DEFUN C:REW_MARK_SPAN ( / POLYLINE_ENTITY POINT1 POINT2 TEMP_DISTANCE1 TEMP_DISTANCE2 I XLINE1_CORD XLINE2_CORD)

  (SETQ POLYLINE_ENTITY TRACK)
  (SETQ XLINE1_CORD (getpropertyvalue (car(entsel "SELECT XLINE1")) "BasePoint"))
  (WHILE (> 1 0)
  (SETQ XLINE2_CORD (getpropertyvalue (CAR(ENTSEL "SELECT XLINE2")) "BasePoint"))
  (SETQ POINT1 (vlax-curve-getClosestPointTo TRACK XLINE1_CORD T))
  (SETQ POINT2 (vlax-curve-getClosestPointTo TRACK XLINE2_CORD T))
  (SETQ MID_CORD (list (/ (+ (car POINT1) (car POINT2)) 2) (/ (+ (cadr POINT1) (cadr POINT2)) 2) 0.0))
  (SETQ MID_CORD2 (list (/ (+ (+ (car POINT1) 20) (car POINT2)) 2) (/ (+ (cadr POINT1) (cadr POINT2)) 2) 0.0))
  (SETQ TEMP_DISTANCE1 (VLAX-CURVE-GETDISTATPOINT POLYLINE_ENTITY POINT1))
  (SETQ TEMP_DISTANCE2 (VLAX-CURVE-GETDISTATPOINT POLYLINE_ENTITY POINT2))
  (COMMAND "MTEXT" MID_CORD MID_CORD2 (RTOS (ABS (- TEMP_DISTANCE1 TEMP_DISTANCE2)) 2 2) "")
  (SETPROPERTYVALUE (entlast) "Rotation" (+ (angle POINT1 POINT2)))
  (SETQ XLINE1_CORD XLINE2_CORD)
  )
)
(DEFUN MARK_SPAN (XL1 XL2 / POLYLINE_ENTITY POINT1 POINT2 TEMP_DISTANCE1 TEMP_DISTANCE2 I XLINE1_CORD XLINE2_CORD)

  (SETQ POLYLINE_ENTITY TRACK)
  (SETQ XLINE1_CORD (getpropertyvalue XL1 "BasePoint"))
  (SETQ XLINE2_CORD (getpropertyvalue XL2 "BasePoint"))
  (SETQ POINT1 (vlax-curve-getClosestPointTo TRACK XLINE1_CORD T))
  (SETQ POINT2 (vlax-curve-getClosestPointTo TRACK XLINE2_CORD T))
  (SETQ MID_CORD (list (/ (+ (car POINT1) (car POINT2)) 2) (/ (+ (cadr POINT1) (cadr POINT2)) 2) 0.0))
  (SETQ MID_CORD2 (list (/ (+ (+ (car POINT1) 20) (car POINT2)) 2) (/ (+ (cadr POINT1) (cadr POINT2)) 2) 0.0))
  (SETQ TEMP_DISTANCE1 (VLAX-CURVE-GETDISTATPOINT POLYLINE_ENTITY POINT1))
  (SETQ TEMP_DISTANCE2 (VLAX-CURVE-GETDISTATPOINT POLYLINE_ENTITY POINT2))
  (COMMAND "MTEXT" MID_CORD MID_CORD2 (RTOS (ABS (- TEMP_DISTANCE1 TEMP_DISTANCE2)) 2 2) "")
  (SETPROPERTYVALUE (entlast) "Rotation" (+ (angle POINT1 POINT2)))
  (SETQ XLINE1_CORD XLINE2_CORD)
)
(DEFUN C:PEG ( / POLYLINE_ENTITY COPY_ENTITY POINT1 POINT2 OS_MODE 3DOS_MODE DIRECTION TEMP_DISTANCE I TEMP_ELE DIST NEXT_POINT TEMP_ELE )
  (COMMAND "UCS" "W")
  (SETQ POLYLINE_ENTITY TRACK)
  (SETQ COPY_ENTITY (CAR(ENTSEL "\n SELECT XLINE")))
  (SETQ XLINE_CORD (getpropertyvalue COPY_ENTITY "BasePoint"))
  (SETQ POINT1 (vlax-curve-getClosestPointTo TRACK XLINE_CORD T))
  (SETQ POINT2 (vlax-curve-getClosestPointTo TRACK (GETPOINT "\n PICK THE SIDE YOU WANT TO PLACE PEG-MARKING") T))
  (SETQ OS_MODE (GETVAR "OSMODE"))
  (SETQ 3DOS_MODE (GETVAR "3DOSMODE"))
  (SETVAR "OSMODE" 0)
  (SETVAR "3DOSMODE" 0)
  (SETQ DIRECTION (FIND_DIRECTION POLYLINE_ENTITY POINT1 POINT2))
  (SETQ TEMP_DISTANCE (VLAX-CURVE-GETDISTATPOINT POLYLINE_ENTITY POINT1))
  (SETQ I 0 TEMP_ELE NIL DIST 0)
  (WHILE (/= DIST NIL)
    (SETQ DIST (GETREAL "\n ENTER DISTANCE"))
    (IF (/= DIST NIL)
    (PROGN
	(IF (= (REM DIST 4.5) 0)
	(PROGN
    (IF (= DIRECTION "POSITIVE")
      (SETQ TEMP_DISTANCE (- TEMP_DISTANCE DIST))
      (SETQ TEMP_DISTANCE (+ TEMP_DISTANCE DIST))
    )
    (SETQ NEXT_POINT (VLAX-CURVE-GETPOINTATDIST POLYLINE_ENTITY TEMP_DISTANCE))
    (SETQ TEMP_ELE (COPY_ORTHOGONAL POLYLINE_ENTITY COPY_ENTITY POINT1 NEXT_POINT TEMP_DISTANCE))
	(SETQ XL_OLD COPY_ENTITY)
    (SETQ COPY_ENTITY (NTH 0 TEMP_ELE) POINT1 (NTH 1 TEMP_ELE))
    )
	(PROGN
	(ALERT "THE SPAN IS NOT STANDARD")
	)
    )
	)
	)
	(MARK_SPAN XL_OLD COPY_ENTITY)
  )
  
  (SETVAR "OSMODE" OS_MODE)
  (SETVAR "3DOSMODE" 3DOS_MODE)
  (COMMAND "UCS" "P")
)
(DEFUN C:CPEG ( / POLYLINE_ENTITY COPY_ENTITY POINT1 POINT2 OS_MODE 3DOS_MODE DIRECTION TEMP_DISTANCE I TEMP_ELE DIST NEXT_POINT TEMP_ELE )
  (COMMAND "UCS" "W")
  (SETQ POLYLINE_ENTITY TRACK)
  (SETQ COPY_ENTITY (CAR(ENTSEL "\n SELECT XLINE")))
  (SETQ XLINE_CORD (getpropertyvalue COPY_ENTITY "BasePoint"))
  (SETQ POINT1 (vlax-curve-getClosestPointTo TRACK XLINE_CORD T))
  (SETQ POINT2 (vlax-curve-getClosestPointTo TRACK (GETPOINT "\n PICK THE SIDE YOU WANT TO PLACE PEG-MARKING") T))
  (SETQ OS_MODE (GETVAR "OSMODE"))
  (SETQ 3DOS_MODE (GETVAR "3DOSMODE"))
  (SETVAR "OSMODE" 0)
  (SETVAR "3DOSMODE" 0)
  (SETQ DIRECTION (FIND_DIRECTION POLYLINE_ENTITY POINT1 POINT2))
  (SETQ TEMP_DISTANCE (VLAX-CURVE-GETDISTATPOINT POLYLINE_ENTITY POINT1))
  (SETQ I 0 TEMP_ELE NIL DIST 0)
  (WHILE (/= DIST NIL)
    (SETQ DIST (GETREAL "\n ENTER DISTANCE"))
    (IF (/= DIST NIL)
    (PROGN
    (IF (= DIRECTION "POSITIVE")
      (SETQ TEMP_DISTANCE (- TEMP_DISTANCE DIST))
      (SETQ TEMP_DISTANCE (+ TEMP_DISTANCE DIST))
    )
    (SETQ NEXT_POINT (VLAX-CURVE-GETPOINTATDIST POLYLINE_ENTITY TEMP_DISTANCE))
    (SETQ TEMP_ELE (COPY_ORTHOGONAL POLYLINE_ENTITY COPY_ENTITY POINT1 NEXT_POINT TEMP_DISTANCE))
    (SETQ COPY_ENTITY (NTH 0 TEMP_ELE) POINT1 (NTH 1 TEMP_ELE))
    )
    )
  )
  (SETVAR "OSMODE" OS_MODE)
  (SETVAR "3DOSMODE" 3DOS_MODE)
  (COMMAND "UCS" "P")
)
(defun c:place_km_stones ()
(COMMAND "UCS" "W")
 (SETQ TRACK_ENTITY_UPTRACK (CAR(ENTSEL "SEECT DN MAIN TRACK")))
 (SETQ COPY_ENTITY (car (ENTSEL "\n SELECT DFCC XLINE")))
  (SETQ NUMBER (GETINT "\n ENTER KM TOTAL NO. OF DFCC KM STONES"))
  (SETQ KM2 (GETSTRING "\n ENTER STARTING DFCC KM IN LOP"))
 (SETQ KM (GETSTRING "\n ENTER STARTING CONT KM IN LOP"))
   (SETQ XLINE_CORD (getpropertyvalue COPY_ENTITY "BasePoint"))
  (SETQ WPT1 (vlax-curve-getClosestPointTo TRACK_ENTITY_UPTRACK XLINE_CORD T))
  (SETQ WPT2 (LAST (POLYLINE_POINTS (LIST TRACK_ENTITY_UPTRACK))))
    (SETQ DIST (GETREAL "\n ENTER DFCC-CONTINUOUS CORRELATION"))
   (SETQ POINT1 WPT1)
  (SETQ POINT2 WPT2)
  (SETVAR "OSMODE" 0)
  (SETVAR "3DOSMODE" 0)
  (SETQ DIRECTION (FIND_DIRECTION TRACK_ENTITY_UPTRACK  POINT1 POINT2))
  (SETQ TEMP_DISTANCE (VLAX-CURVE-GETDISTATPOINT TRACK_ENTITY_UPTRACK  POINT1))
  (SETQ I 0 TEMP_ELE NIL)
    (IF (/= DIST NIL)
    (PROGN
    (IF (= DIRECTION "POSITIVE")
      (SETQ TEMP_DISTANCE (- TEMP_DISTANCE DIST))
      (SETQ TEMP_DISTANCE (+ TEMP_DISTANCE DIST))
    )
    (SETQ NEXT_POINT (VLAX-CURVE-GETPOINTATDIST TRACK_ENTITY_UPTRACK  TEMP_DISTANCE))
    (SETQ TEMP_ELE (COPY_ORTHOGONAL TRACK_ENTITY_UPTRACK  COPY_ENTITY POINT1 NEXT_POINT TEMP_DISTANCE))
    (SETQ COPY_ENTITY (NTH 0 TEMP_ELE) POINT1 (NTH 1 TEMP_ELE))
    )
    )
	(SETQ COPY_ENTITY2 (CDR (ASSOC -1 (ENTGET(ENTLAST)))))
	(SETQ XLINE_CORD2 (getpropertyvalue COPY_ENTITY2 "BasePoint"))
  (SETQ WPT3 (vlax-curve-getClosestPointTo TRACK_ENTITY_UPTRACK XLINE_CORD2 T))
  (SETQ WPT4 WPT2)
  (ENTDEL (ENTLAST))
   (SETQ DIRECTION (FIND_DIRECTION TRACK_ENTITY_UPTRACK WPT3 WPT4))
 (SETQ KM_STONE_LIST (INSERT_KM_STONE_GPS TRACK_ENTITY_UPTRACK WPT3 NUMBER DIRECTION))
 (SETQ I 0)
 (WHILE (< I (LENGTH KM_STONE_LIST))
 (setpropertyvalue (NTH 0 (NTH I KM_STONE_LIST)) "Color" "5")
  (MODIFY_ATTRIBUTES (NTH 0 (NTH I KM_STONE_LIST)) (LIST "KM" "LEFT_KM" "RIGHT_KM") (LIST (STRCAT "%%UCONT KM:" KM) (STRCAT (ITOA (- (ATOI KM) 1)) "/1000.00" ) (STRCAT (ITOA (ATOI KM)) "/0000.00" )))
  (SETQ KM (ITOA (+ (ATOI KM) 1)))
  (SETQ I (+ I 1))
 )
 (SETQ DIRECTION2 (FIND_DIRECTION TRACK_ENTITY_UPTRACK WPT1 WPT2))
 (SETQ NUMBER2 NUMBER)
 (SETQ KM_STONE_LIST2 (INSERT_KM_STONE_GPS1 TRACK_ENTITY_UPTRACK WPT1 NUMBER2 DIRECTION2))
 (SETQ J 0)
 (WHILE (< J (LENGTH KM_STONE_LIST2))
 (setpropertyvalue (NTH 0 (NTH J KM_STONE_LIST2)) "Color" "1")
  (MODIFY_ATTRIBUTES (NTH 0 (NTH J KM_STONE_LIST2)) (LIST "KM" "LEFT_KM" "RIGHT_KM") (LIST (STRCAT "%%UKM:" KM2) (STRCAT (ITOA (- (ATOI KM2) 1)) "/1000.00" ) (STRCAT (ITOA (ATOI KM2)) "/0000.00" )))
  (SETQ KM2 (ITOA (+ (ATOI KM2) 1)))
  (SETQ J (+ J 1))
 )
)
(defun C:G-TYPE ( / I BLOCKS_LIST BLOCK)
(setq WPT1 (GETPOINT "\n PICK POINT1"))
(setq WPT2 (GETPOINT "\n PICK POINT2"))
(setq WPT3 (GETPOINT "\n PICK POINT3"))
(setq WPT4 (GETPOINT "\n PICK POINT4"))
(YARD_MAST_DATA WPT1 WPT2 WPT3 WPT4)
(setq BLOCK_LIST PORTAL_LIST)
(SETQ I 0)
(WHILE (< I (LENGTH PORTAL_LIST))
(SETQ BLOCK (NTH I PORTAL_LIST))
;(sETQ BLOCK (CAR (ENTSEL)))
(SETQ MAST_TYPE (GET_ATTRIBUTE_VALUE "MAST_TYPE1" BLOCK))
(IF ( = MAST_TYPE "G-TYPE")
(PROGN
(setpropertyvalue BLOCK "Color" "4")
)
)
(SETQ I (+ 1 I))
)
)

(defun C:ACC_COUNT (/ i)
	(setq temp_wire (entsel ""))
	(setq wire_point_list (POLYLINE_POINTS temp_wire))
	(setq i 0)
	(while (< i (length wire_point_list))
		(setq temp_point (nth i wire_point_list))
		(setq temp_point_proj (vlax-curve-getClosestPointTo TRACK temp_point T))
		(command "XLINE" temp_point temp_point_proj "")
		(setq i (+ i 1))
	)
)
(defun C:SHOW_BKT_VIEW_LOC (/ TRIPLE_LIST DOUBLE_LIST)
(setq WPT1 (GETPOINT "\n PICK POINT1"))
(setq WPT2 (GETPOINT "\n PICK POINT2"))
(setq WPT3 (GETPOINT "\n PICK POINT3"))
(setq WPT4 (GETPOINT "\n PICK POINT4"))
(YARD_MAST_DATA WPT1 WPT2 WPT3 WPT4)
(setq TRIPLE_LIST (append TRIPLE_CANT_DA_LIST TRIPLE_CANT_MAST_LIST TRIPLE_CANT_UR_LIST))
(setq DOUBLE_LIST (append DOUBLE_CANT_DA_LIST DOUBLE_CANT_MAST_LIST DOUBLE_CANT_UR_LIST))
(setq u 0)
(while (< u (length TRIPLE_LIST))
	(if (/= (getpropertyvalue (nth u triple_list) "color") "3")
	(progn
	(setpropertyvalue (nth u TRIPLE_LIST) "Color" "4")
	(MARK (nth u TRIPLE_LIST))
	)
	)
	(setq u (+ 1 u))
)
(setq j 0)
(while (< j (length DOUBLE_LIST))
	(setq TS (GET_ATTRIBUTE_VALUE "TS" (nth j DOUBLE_LIST)))
	(IF (and (/= (getpropertyvalue (nth u double_list) "color") "3")(and (/= TS "XXX")(/= TS "TS=XXX")))
	(PROGN
		(setpropertyvalue (nth J DOUBLE_LIST) "Color" "4")
		(MARK (nth J DOUBLE_LIST))
	)
	)
	(setq J (+ 1 J))
)
)
(defun MARK (BLOCK_ENTITY)
(setq BLOCK_ENTITY_CORD (OBJECT_CORDINATES (LIST BLOCK_ENTITY)))
(SETQ BLOCK_ENTITY_CORD_PROJ (vlax-curve-getClosestPointTo TRACK BLOCK_ENTITY_CORD T))
(COMMAND "XLINE" BLOCK_ENTITY_CORD BLOCK_ENTITY_CORD_PROJ "")
)
(defun C:SHOW_MAIN_SUPPORTED ( / i MAST_LIST)
(setq WPT1 (GETPOINT "\n PICK POINT1"))
(setq WPT2 (GETPOINT "\n PICK POINT2"))
(setq WPT3 (GETPOINT "\n PICK POINT3"))
(setq WPT4 (GETPOINT "\n PICK POINT4"))
(YARD_MAST_DATA WPT1 WPT2 WPT3 WPT4)
(SETQ MAST_LIST (APPEND SINGLE_CANT_DA_LIST DOUBLE_CANT_DA_LIST TRIPLE_CANT_DA_LIST SINGLE_CANT_MAST_LIST DOUBLE_CANT_MAST_LIST TRIPLE_CANT_MAST_LIST SINGLE_CANT_UR_LIST DOUBLE_CANT_UR_LIST TRIPLE_CANT_UR_LIST))
(setq i 0)
(while (< i (length MAST_LIST))
(if (= (getpropertyvalue (nth i MAST_LIST) "color") "3")
(progn
(MARK (nth i MAST_LIST))
)
)
(setq i (+ 1 i))
)
)
(defun C:SHOW_LOOP_MASTS ( / i MAST_LIST)
(setq WPT1 (GETPOINT "\n PICK POINT1"))
(setq WPT2 (GETPOINT "\n PICK POINT2"))
(setq WPT3 (GETPOINT "\n PICK POINT3"))
(setq WPT4 (GETPOINT "\n PICK POINT4"))
(YARD_MAST_DATA WPT1 WPT2 WPT3 WPT4)
(SETQ MAST_LIST (APPEND SINGLE_CANT_MAST_LIST DOUBLE_CANT_MAST_LIST TRIPLE_CANT_MAST_LIST PORTAL_LIST TTC_LIST SS0_LIST))
(setq i 0)
(while (< i (length MAST_LIST))
(if (/= (getpropertyvalue (nth i MAST_LIST) "color") "3")
(progn
(MARK (nth i MAST_LIST))
)
)
(setq i (+ 1 i))
)
)
(defun C:CSD_COPY ( / Source_block Destination_block MAST_TYPE FDN RD ANCHOR_DETAILS)
(setq Source_block (car(entsel "Select the source Block")))
(setq Destination_block (car(entsel "Select the Destination Block")))
(setq MAST_TYPE (GET_ATTRIBUTE_VALUE "MAST_TYPE1" SOURCE_BLOCK))
(setq FDN (GET_ATTRIBUTE_VALUE "FOUNDATION_TYPE1" SOURCE_BLOCK))
(setq ANCHOR_DETAILS (GET_ATTRIBUTE_VALUE "ANCHOR_BLOCK/ANCHOR_STEP/ANCHOR_SETTING_DISTANCE" SOURCE_BLOCK))
(setq RD (GET_ATTRIBUTE_VALUE "RD1" SOURCE_BLOCK))
(setq SD (GET_ATTRIBUTE_VALUE "STEP_DISTANCE/EMBEDDED_LENGTH" SOURCE_BLOCK))
(setq SB (GET_ATTRIBUTE_VALUE "SUPER_BLOCK/EXTRA_DEPTH" SOURCE_BLOCK))
(setq SE (GET_ATTRIBUTE_VALUE "RADIUS/SUPER_ELEVATION" SOURCE_BLOCK))
(MODIFY_ATTRIBUTES DESTINATION_BLOCK (LIST "MAST_TYPE1" "FOUNDATION_TYPE1" "RD1" "ANCHOR_BLOCK/ANCHOR_STEP/ANCHOR_SETTING_DISTANCE" "STEP_DISTANCE/EMBEDDED_LENGTH" "SUPER_BLOCK/EXTRA_DEPTH" "RADIUS/SUPER_ELEVATION") (LIST MAST_TYPE FDN RD ANCHOR_DETAILS SD SB SE))
)
(DEFUN C:LOAD_SE ( / ) ; loads the HRL excel sheet
  (OPENEXCEL (FINDFILE (GETFILED "SELECT SE FILE" "" "" 8)) "SE" T)
)
(DEFUN C:PRINT_SE ( / ) ; Prints the HRL in the masts
(SETQ START_CELL (GETSTRING "\N ENTER STARTING CELL"))
(SETQ END_CELL (GETSTRING "\N ENTER ENDING CELL"))
(setq MODE (GETSTRING "ENTER MODE OF OPERATION : MANUAL->M | AUTOMATIC->A"))
(IF (= MODE "A")
(PROGN
(setq WPT1 (GETPOINT "\n PICK POINT1"))
(setq WPT2 (GETPOINT "\n PICK POINT2"))
(setq WPT3 (GETPOINT "\n PICK POINT3"))
(setq WPT4 (GETPOINT "\n PICK POINT4"))
(YARD_MAST_DATA WPT1 WPT2 WPT3 WPT4)
(setq BLOCK_LIST MAST_LIST)
))
(setq BLOCK_LIST MAST_LIST)
(SETQ CHAINAGE_LIST (getCellsrow/column "SE" (STRCAT (COLUMN+N START_CELL 0) ":" (COLUMN+N END_CELL 0))))
(SETQ SE_LIST (getCellsrow/column "SE" (STRCAT (COLUMN+N START_CELL 1) ":" (COLUMN+N END_CELL 1))))
(SETQ I 0)
(WHILE (IF (= MODE "M") (PROGN (> 1 0))(PROGN (< I (LENGTH BLOCK_LIST))))
(IF (= MODE "M")
(PROGN
(setq BLOCK (entsel "Select the BLOCK : "))
)
)
(IF (= MODE "A")
(PROGN
(setq BLOCK (LIST (NTH I BLOCK_LIST)))
)
)
(setq BLOCK_NAME (getpropertyvalue (CAR BLOCK) "BlockTableRecord/Name"))
(IF(OR (= BLOCK_NAME "SS0") (= BLOCK_NAME "TRIPLE_CANT_MAST") (= BLOCK_NAME "DOUBLE_CANT_MAST") (= BLOCK_NAME "SINGLE_CANT_MAST"))
(PROGN
(SETQ BLOCK_CHAIN (NTH 1 (ASSOC "CHAINAGE2" (GET_ATTRIBUTES (CAR BLOCK)))))
(SETQ SLASH_LOC (vl-string-search "/" BLOCK_CHAIN))
(SETQ STR1 (SUBSTR BLOCK_CHAIN 1 SLASH_LOC))
(SETQ STR2 (SUBSTR BLOCK_CHAIN (+ 2 SLASH_LOC)))
(WHILE (< (STRLEN STR2) 6)
(PROGN
(SETQ STR2 (STRCAT "0" STR2))
)
)
(SETQ CH (ATOF (STRCAT (STRCAT STR1 STR2))))
)
)
(SETQ J 0)
(WHILE (< J (LENGTH CHAINAGE_LIST))
(IF (> CH (NTH J CHAINAGE_LIST))
(PROGN 
(SETQ SE_BLOCK (NTH J SE_LIST))
(MODIFY_ATTRIBUTES (CAR BLOCK) (LIST "RADIUS/SUPER_ELEVATION") (LIST SE_BLOCK))
)
)
(SETQ J (+ 1 J))
)
(IF (= MODE "A")
(PROGN
(setq I (+ 1 I))
)
)
)
)

(defun Mast_side (Mast)
(setq Temp_mast (car mast))
(setq DN_DIST (distance (object_cordinates (list temp_mast)) (vlax-curve-getClosestPointTo TRACK (object_cordinates (list temp_mast)))))
(setq UP_DIST (distance (object_cordinates (list temp_mast)) (vlax-curve-getClosestPointTo UP_TRACK (object_cordinates (list temp_mast)))))
(if (> DN_DIST UP_DIST)
(PROGN 
(setq Side "UP")
)
(PROGN
(setq Side "DN")
)
)
)
;
;;;;;;;;;;;;;;;;;;;;_____________________________________________________________________EXCEL SHEET SUPPORTING FUNCTIONS__________________________________________________________________________________________________
;;;;;;;;;;;;;;;;;;;;;;;;;;;;
;;;;;;;;;;;;;;;;;;;;;;;;;;;;;;;
(defun getCellsrow/column
       (sheetName cellName / myXL myBook mySheet myRange cellValue)
  (setq mybook *EXCELAPP%)
  (setq	mySheet	(vl-catch-all-apply
		  'vlax-get-property
		  (list	(vlax-get-property myBook "Sheets")
			"Item"
			sheetName
		  )
		)
  )
  (vlax-invoke-method mySheet "Activate")
  (setq	myRange	(vlax-get-property
		  (vlax-get-property mySheet 'Cells)
		  "Range"
		  cellName
		)
  )
  (setq
    cellValue (vlax-variant-value (vlax-get-property myRange 'Value2))
  )


  (if (= 'safearray (type cellValue))
    (progn
      (setq tempCellValue (vlax-safearray->list cellValue))
      (setq cellValue (list))
      (if (= (length tempCellValue) 1)
	(progn
	  (foreach a tempCellValue
	    (if	(= (type a) 'LIST)
	      (progn
		(foreach b a
		  (if (= (type b) 'LIST)
		    (setq
		      cellValue	(append
				  cellValue
				  (list (vlax-variant-value (car b)))
				)
		    )
		    (setq
		      cellValue	(append	cellValue
					(list (vlax-variant-value b))
				)
		    )
		  )
		)
	      )
	      (setq cellValue (append cellValue
				      (list (vlax-variant-value a))
			      )
	      )
	    )
	  )
	)
	(progn
	  (foreach a tempCellValue
	    (setq tmpList (list))
	    (foreach b a
	      (setq tmp (vlax-variant-value b))
	      (setq tmpList (append tmpList (list tmp)))
	    )
	    (setq cellValue (append cellValue tmpList))
	  )
	)
      )
    )
  )
  cellValue
)
(DEFUN ALPHA2NUMBER (STR$ / NUM#)
  (IF (= 0 (SETQ NUM# (STRLEN STR$)))
    0
    (+ (* (- (ASCII (STRCASE (SUBSTR STR$ 1 1))) 64)
	  (EXPT 26 (1- NUM#))
       )
       (ALPHA2NUMBER (SUBSTR STR$ 2))
    )					;+
  )					;IF
)					;DEFUN ALPHA2NUMBER
(DEFUN NUMBER2ALPHA (NUM# / VAL#)
  (IF (< NUM# 27)
    (CHR (+ 64 NUM#))
    (IF	(= 0 (SETQ VAL# (REM NUM# 26)))
      (STRCAT (NUMBER2ALPHA (1- (/ NUM# 26))) "Z")
      (STRCAT (NUMBER2ALPHA (/ NUM# 26)) (CHR (+ 64 VAL#)))
    )					;IF
  )					;IF
)					;DEFUN NUMBER2ALPHA
(DEFUN CELL-P (CELL$)
  (AND (= (TYPE CELL$) 'STR)
       (OR (= (STRCASE CELL$) "A1")
	   (NOT (EQUAL (COLUMNROW CELL$) '(1 1)))
       )				;OR
  )					;AND
)					;DEFUN CELL-P

(DEFUN RTOSR (REALNUM~ / DIMZIN# SHORTREAL$)
  (SETQ DIMZIN# (GETVAR "DIMZIN"))
  (SETVAR "DIMZIN" 8)
  (SETQ SHORTREAL$ (RTOS REALNUM~ 2 8))
  (SETVAR "DIMZIN" DIMZIN#)
  SHORTREAL$
)					;DEFUN RTOSR
(DEFUN COLUMNROW (CELL$ / COLUMN$ CHAR$ ROW#)
  (SETQ COLUMN$ "")
  (WHILE (< 64 (ASCII (SETQ CHAR$ (STRCASE (SUBSTR CELL$ 1 1)))) 91)
    (SETQ COLUMN$ (STRCAT COLUMN$ CHAR$)
	  CELL$	  (SUBSTR CELL$ 2)
    )					;SETQ
  )					;WHILE
  (IF (AND (/= COLUMN$ "") (NUMBERP (SETQ ROW# (READ CELL$))))
    (LIST (ALPHA2NUMBER COLUMN$) ROW#)
    '(1 1)				;DEFAULT TO "A1" IF THERE'S A PROBLEM
  )					;IF
)					;DEFUN COLUMNROW
(DEFUN ROW+N (CELL$ NUM#)
  (SETQ CELL$ (COLUMNROW CELL$))
  (STRCAT (NUMBER2ALPHA (CAR CELL$))
	  (ITOA (MAX 1 (+ (CADR CELL$) NUM#)))
  )
)					;DEFUN ROW+N
(DEFUN COLUMN+N	(CELL$ NUM#)
  (SETQ CELL$ (COLUMNROW CELL$))
  (STRCAT (NUMBER2ALPHA (MAX 1 (+ (CAR CELL$) NUM#)))
	  (ITOA (CADR CELL$))
  )
)					;DEFUN COLUMN+N
(DEFUN OPENEXCEL
       (EXCELFILE$ SHEETNAME$ VISIBLE / SHEET$ SHEETS@ WORKSHEET)
  (IF (= (TYPE EXCELFILE$) 'STR)
    (IF	(FINDFILE EXCELFILE$)
      (SETQ *EXCELFILE$ EXCELFILE$)
      (PROGN
	(ALERT (STRCAT "EXCEL FILE " EXCELFILE$ " NOT FOUND."))
	(EXIT)
      )					;PROGN
    )					;IF
    (SETQ *EXCELFILE$ "")
  )					;IF
  (GC)
  (IF (SETQ *EXCELAPP% (VLAX-GET-OBJECT "EXCEL.APPLICATION"))
    (PROGN
      (ALERT "CLOSE ALL EXCEL SPREADSHEETS TO CONTINUE!")
      (VLAX-RELEASE-OBJECT *EXCELAPP%)
      (GC)
    )					;PROGN
  )					;IF
  (SETQ *EXCELAPP% (VLAX-GET-OR-CREATE-OBJECT "EXCEL.APPLICATION"))
  (IF EXCELFILE$
    (IF	(FINDFILE EXCELFILE$)
      (VLAX-INVOKE-METHOD
	(VLAX-GET-PROPERTY *EXCELAPP% 'WORKBOOKS)
	'OPEN
	EXCELFILE$
      )
      (VLAX-INVOKE-METHOD
	(VLAX-GET-PROPERTY *EXCELAPP% 'WORKBOOKS)
	'ADD
      )
    )					;IF
    (VLAX-INVOKE-METHOD
      (VLAX-GET-PROPERTY *EXCELAPP% 'WORKBOOKS)
      'ADD
    )
  )					;IF
  (IF VISIBLE
    (VLA-PUT-VISIBLE *EXCELAPP% :VLAX-TRUE)
  )					;IF
  (IF (= (TYPE SHEETNAME$) 'STR)
    (PROGN
      (VLAX-FOR	SHEET$ (VLAX-GET-PROPERTY *EXCELAPP% "SHEETS")
	(SETQ SHEETS@ (APPEND SHEETS@
			      (LIST (VLAX-GET-PROPERTY SHEET$ "NAME"))
		      )
	)
      )					;VLAX-FOR
      (IF (MEMBER SHEETNAME$ SHEETS@)
	(VLAX-FOR WORKSHEET (VLAX-GET-PROPERTY *EXCELAPP% "SHEETS")
	  (IF (= (VLAX-GET-PROPERTY WORKSHEET "NAME") SHEETNAME$)
	    (VLAX-INVOKE-METHOD WORKSHEET "ACTIVATE")
	  )				;IF
	)				;VLAX-FOR
	(VLAX-PUT-PROPERTY
	  (VLAX-INVOKE-METHOD
	    (VLAX-GET-PROPERTY *EXCELAPP% "SHEETS")
	    "ADD"
	  )
	  "NAME"
	  SHEETNAME$
	)
      )					;IF
    )					;PROGN
  )					;IF
  (PRINC)
)
(defun c:swap_cordinates()
(while (> 1 0)
(setq object1 (vlax-ename->vla-object (car (entsel "TABLE 1"))))
(setq object2 (vlax-ename->vla-object (car (entsel "TABLE 2"))))
(vla-put-color object1 1)
(vla-put-color object2 1)
(SETQ TABLE1_COR (vla-gettext  object1 5 0))
(SETQ TABLE2_COR (vla-gettext  object2 5 0))
(vla-settext object1 5 0 TABLE2_COR)
(vla-settext object2 5 0 TABLE1_COR)
)
)
(DEFUN FIND_DIRECTION (POLYLINE_ENTITY POINT1 POINT2 / X )
  (SETQ X (- (VLAX-CURVE-GETDISTATPOINT POLYLINE_ENTITY POINT1) (VLAX-CURVE-GETDISTATPOINT POLYLINE_ENTITY POINT2)))
  (IF (= (+ X (ABS X)) 0) "NEGATIVE" "POSITIVE")
)
(DEFUN COPY_ORTHOGONAL (POLYLINE_ENTITY OBJECT PREVIOUS_POINT POINT DIST / ANGLE1 DERIVATIVE SLOPE OBJECT1 POINTS_LIST OBJECT_VLA)
(SETQ ANGLE1 (VLAX-CURVE-GETPARAMATPOINT POLYLINE_ENTITY POINT))
(SETQ DERIVATIVE (VLAX-CURVE-GETFIRSTDERIV POLYLINE_ENTITY ANGLE1))
(SETQ SLOPE (+ (/ PI 2) (ANGLE '(0 0 0) DERIVATIVE)))
(COMMAND "COPY" OBJECT "" PREVIOUS_POINT POINT)
(SETQ OBJECT1 (ENTLAST))
(SETQ POINTS_LIST (ADD_LISTS (BUILD_LIST (FILTER_LIST (LIST 10 11) (ENTGET OBJECT1) 0) (LIST 1 2)) (N_ELE_LIST 0.0 2)))
(SETQ OBJECT_VLA (VLAX-ENAME->VLA-OBJECT OBJECT1))
;(VLAX-INVOKE-METHOD (VLAX-ENAME->VLA-OBJECT OBJECT1) "ROTATE" (VLAX-3D-POINT (VLAX-CURVE-GETPOINTATDIST POLYLINE_ENTITY DIST)) (- (VLAX-GET-PROPERTY (VLAX-ENAME->VLA-OBJECT OBJECT1) "ANGLE") SLOPE))
(IF (/= (CDR(ASSOC 0 (ENTGET OBJECT1))) "XLINE")
  (COMMAND "ROTATE" OBJECT1 "" (VLAX-CURVE-GETPOINTATDIST POLYLINE_ENTITY DIST) "R" (NTH 0 POINTS_LIST) (NTH 1 POINTS_LIST) (/ (* SLOPE 180) PI))
  (COMMAND "ROTATE" OBJECT1 "" (VLAX-CURVE-GETPOINTATDIST POLYLINE_ENTITY DIST) "R" (VLAX-SAFEARRAY->LIST (VLAX-VARIANT-VALUE (VLAX-GET-PROPERTY OBJECT_VLA "BASEPOINT"))) (VLAX-SAFEARRAY->LIST (VLAX-VARIANT-VALUE (VLAX-GET-PROPERTY OBJECT_VLA "SECONDPOINT"))) (/ (* SLOPE 180) PI))
)
(LIST OBJECT1 POINT)
)
(DEFUN FILTER_LIST (LIST1 LIST2 POSITION / I LOOP_ELE TEMP_ELE LIST3)
  (SETQ I 0)
  (SETQ LIST3 NIL)
  (WHILE (< I (LENGTH LIST2))
    (SETQ LOOP_ELE (NTH POSITION (NTH I LIST2)))
    (IF	(>= (VL-POSITION LOOP_ELE LIST1) 0)
      (PROGN (SETQ TEMP_ELE (NTH I LIST2))
	     (SETQ LIST3 (CONS TEMP_ELE LIST3))
      )
    )
    (SETQ I (+ I 1))
  )
  (SETQ LIST3 (REVERSE LIST3))
)
(DEFUN BUILD_LIST (LIST1 LIST2 / I J LIST3 TEMP_ELE TEMP_ELE1)
  (SETQ I 0)
  (SETQ LIST3 NIL)
  (WHILE (< I (LENGTH LIST1))
    (SETQ TEMP_ELE (NTH I LIST1))
    (SETQ J 0)
    (SETQ TEMP_ELE1 NIL)
    (WHILE (< J (LENGTH LIST2))
      (SETQ TEMP_ELE1 (CONS (NTH (NTH J LIST2) TEMP_ELE) TEMP_ELE1))
      (SETQ J (+ J 1))
    )
    (SETQ TEMP_ELE1 (REVERSE TEMP_ELE1))
    (SETQ LIST3 (CONS TEMP_ELE1 LIST3))
    (SETQ I (+ I 1))
  )
  (SETQ LIST3 (REVERSE LIST3))
)
(DEFUN N_ELE_LIST (XYZ LEN / I)
  (SETQ I 0)
  (SETQ ELE_LIST NIL)
  (WHILE (< I LEN)
    (SETQ ELE_LIST (CONS XYZ ELE_LIST))
    (SETQ I (+ I 1))
  )
  (SETQ ELE_LIST (REVERSE ELE_LIST))
)
(DEFUN ADD_LISTS (LIST1 LIST2 / I TEMP_ELE MAIN_LIST)
  (SETQ I 0)
  (SETQ MAIN_LIST NIL)
  (WHILE (< I (LENGTH LIST1))
    (IF	(AND (VL-CONSP (NTH I LIST1)) (VL-CONSP (NTH I LIST2)))
      (PROGN (SETQ TEMP_ELE (APPEND (NTH I LIST1) (NTH I LIST2)))
	     (SETQ MAIN_LIST (CONS TEMP_ELE MAIN_LIST))
      )
    )
    (IF	(AND (NOT (VL-CONSP (NTH I LIST1)))
	     (NOT (VL-CONSP (NTH I LIST2)))
	)
      (PROGN (SETQ TEMP_ELE (CONS (NTH I LIST1) (NTH I LIST2)))
	     (SETQ MAIN_LIST (CONS TEMP_ELE MAIN_LIST))
      )
    )
    (IF	(AND (VL-CONSP (NTH I LIST1))
	     (NOT (VL-CONSP (NTH I LIST2)))
	)
      (PROGN (SETQ TEMP_ELE (APPEND (NTH I LIST1) (LIST (NTH I LIST2))))
	     (SETQ MAIN_LIST (CONS TEMP_ELE MAIN_LIST))
      )
    )
    (IF	(AND (NOT (VL-CONSP (NTH I LIST1)))
	     (VL-CONSP (NTH I LIST2))
	)
      (PROGN (SETQ TEMP_ELE (CONS (NTH I LIST1) (NTH I LIST2)))
	     (SETQ MAIN_LIST (CONS TEMP_ELE MAIN_LIST))
      )
    )
    (SETQ I (+ I 1))
  )
  (SETQ MAIN_LIST (REVERSE MAIN_LIST))
)
(defun c:invis (/ ent obj)
  (vl-load-com)

  (while (setq ent (car (nentsel "\nSelect Attribute: ")))
    (if (eq "ATTRIB" (cdr (assoc 0 (entget ent))))
      (vlax-put (setq obj (vlax-ename->vla-object ent)) 'invisible -1)))

  (princ))
  (defun c:invis_all (/ LIST1 FLAG)
  (vl-load-com)
  (SETQ  FLAG (GETSTRING "SELECT VISIBILITY STATE 0/1 VISIBLE-->1 INVISIBLE---->0 :- "))
  (SETQ FLAG1 (GETSTRING "/N SELECT ATTRIBUTE--->S OR ENTER TAG NAME-->E"))
  (IF (= FLAG1 "S")
   (SETQ ATTR_TAG (CDR (ASSOC 2 (ENTGET (CAR (NENTSEL "SELECT ATTRIBUTE"))))))
   (SETQ ATTR_TAG (GETSTRING "/N ENTER TAGNAME : ")))
  (SETQ LIST1 (SSGET))
  (SETQ LIST1 (FORM_SSSET LIST1))
  (SETQ I 0)
  (while (< I (LENGTH LIST1))
      (CHANGE_VISIBILITY (NTH I LIST1) (LIST ATTR_TAG) (LIST FLAG))
      (SETQ  I (+ I 1)))
  (princ))
  (defun c:VIS_ALL_ATTRIBITES (/ LIST1 FLAG) ; USED FOR CONVERTING PEGGING PLANS TO LOP
  (vl-load-com)
  (SETQ  FLAG "1")
  (SETQ FLAG1 "S")
  (IF (= FLAG1 "S")
  (PROGN
   (SETQ ATTR_TAG (CDR (ASSOC 2 (ENTGET (CAR (NENTSEL "SELECT ATTRIBUTE"))))))
   (SETQ ATTR_TAG1 (CDR (ASSOC 2 (ENTGET (CAR (NENTSEL "SELECT ATTRIBUTE"))))))
   (SETQ ATTR_TAG2 (CDR (ASSOC 2 (ENTGET (CAR (NENTSEL "SELECT ATTRIBUTE"))))))
   (SETQ ATTR_TAG3 (CDR (ASSOC 2 (ENTGET (CAR (NENTSEL "SELECT ATTRIBUTE"))))))
   (SETQ ATTR_TAG4 (CDR (ASSOC 2 (ENTGET (CAR (NENTSEL "SELECT ATTRIBUTE"))))))
   (SETQ ATTR_TAG5 (CDR (ASSOC 2 (ENTGET (CAR (NENTSEL "SELECT ATTRIBUTE"))))))
   (SETQ ATTR_TAG6 (CDR (ASSOC 2 (ENTGET (CAR (NENTSEL "SELECT ATTRIBUTE"))))))
   (SETQ ATTR_TAG7 (CDR (ASSOC 2 (ENTGET (CAR (NENTSEL "SELECT ATTRIBUTE"))))))
   (SETQ ATTR_TAG8 (CDR (ASSOC 2 (ENTGET (CAR (NENTSEL "SELECT ATTRIBUTE"))))))
   (SETQ ATTR_TAG9 (CDR (ASSOC 2 (ENTGET (CAR (NENTSEL "SELECT ATTRIBUTE"))))))
   (SETQ ATTR_TAG10 (CDR (ASSOC 2 (ENTGET (CAR (NENTSEL "SELECT ATTRIBUTE"))))))
   (SETQ ATTR_TAG11 (CDR (ASSOC 2 (ENTGET (CAR (NENTSEL "SELECT ATTRIBUTE"))))))
   )
   (PROGN
   (SETQ ATTR_TAG (GETSTRING "/N ENTER TAGNAME : "))
	)
	)
   (SETQ LIST1 (SSGET))
  (SETQ LIST1 (FORM_SSSET LIST1))
  (SETQ I 0)
  (while (< I (LENGTH LIST1))
      (CHANGE_VISIBILITY (NTH I LIST1) (LIST ATTR_TAG) (LIST FLAG))
	  (CHANGE_VISIBILITY (NTH I LIST1) (LIST ATTR_TAG1) (LIST FLAG))
	  (CHANGE_VISIBILITY (NTH I LIST1) (LIST ATTR_TAG2) (LIST FLAG))
	  (CHANGE_VISIBILITY (NTH I LIST1) (LIST ATTR_TAG3) (LIST FLAG))
	  (CHANGE_VISIBILITY (NTH I LIST1) (LIST ATTR_TAG4) (LIST FLAG))
	  (CHANGE_VISIBILITY (NTH I LIST1) (LIST ATTR_TAG5) (LIST FLAG))
	  (CHANGE_VISIBILITY (NTH I LIST1) (LIST ATTR_TAG6) (LIST FLAG))
	  (CHANGE_VISIBILITY (NTH I LIST1) (LIST ATTR_TAG7) (LIST FLAG))
	  (CHANGE_VISIBILITY (NTH I LIST1) (LIST ATTR_TAG8) (LIST FLAG))
	  (CHANGE_VISIBILITY (NTH I LIST1) (LIST ATTR_TAG9) (LIST FLAG))
	  (CHANGE_VISIBILITY (NTH I LIST1) (LIST ATTR_TAG10) (LIST FLAG))
	  (CHANGE_VISIBILITY (NTH I LIST1) (LIST ATTR_TAG11) (LIST FLAG))
	  (CHANGE_VISIBILITY (NTH I LIST1) (LIST ATTR_TAG12) (LIST FLAG))
      (SETQ  I (+ I 1)))
  (princ))
 (DEFUN FORM_SSSET (SSSET / I TEMP_ELE LIST1)
  (SETQ I 0)
  (SETQ TEMP_ELE NIL)
  (SETQ LIST1 NIL_)
  (WHILE (< I (SSLENGTH SSSET))
    (SETQ TEMP_ELE (SSNAME SSSET I))
    (SETQ LIST1 (CONS TEMP_ELE LIST1))
    (SETQ I (+ I 1))
  )
  (REVERSE LIST1)
)
(DEFUN CHANGE_VISIBILITY (ENTNAME     IDENTIFIER  VALUE
			  /	      TEMP_ELE	  ENT_OBJECT
			  SAFEARRAY_SET		  I
			  J	      LIST1
			 )
  (SETQ SAFEARRAY_SET NIL)
  (SETQ ENT_OBJECT ENTNAME)
  (SETQ ENT_OBJECT (VLAX-ENAME->VLA-OBJECT ENT_OBJECT))
  (IF (= (VLAX-GET-PROPERTY ENT_OBJECT "HASATTRIBUTES")
	 :VLAX-TRUE
      )
    (PROGN
      (SETQ SAFEARRAY_SET
	     (VLAX-SAFEARRAY->LIST
	       (VLAX-VARIANT-VALUE
		 (VLAX-INVOKE-METHOD ENT_OBJECT "GETATTRIBUTES")
	       )
	     )
      )

      (SETQ I 0)
      (SETQ J 0)
      (SETQ LIST1 NIL)
      (SETQ TEMP_ELE NIL)
      (WHILE (< I (LENGTH SAFEARRAY_SET))
	(SETQ TEMP_ELE
	       (VLAX-GET-PROPERTY (NTH I SAFEARRAY_SET) "TAGSTRING")
	)
	(IF (/= (VL-POSITION TEMP_ELE IDENTIFIER) NIL)
	  (PROGN
	    (VLAX-PUT-PROPERTY
	      (NTH I SAFEARRAY_SET)
	      "INVISIBLE"
	      (IF (= (NTH (VL-POSITION TEMP_ELE IDENTIFIER) VALUE) "1")
		:VLAX-FALSE
		:VLAX-TRUE
	      )
	    )
	  )
	)
	(SETQ I (+ I 1))
      )
    )
  )
)

;;;;;;;;;;;;;;;;;;;;;;;;;;;;;;;;;;_________________________________________________________________________________________________________________________________________________________________________________________

;_________________________________________________________________________________________FOR KM STONE_________________________________________________________________________________________________________________________
(DEFUN KM_STONE_GPS ( / TRACK_ENTITY_UPTRACK WPT1 WPT2 DIRECTION NUMBER KM KM_STONE_LIST BLOCKS_LIST BLOCK_NAME_LIST KM_STONE_LIST I)
(COMMAND "UCS" "W")
 (SETQ TRACK_ENTITY_UPTRACK (CAR(ENTSEL "SEECT DN MAIN TRACK")))
  (SETQ COPY_ENTITY (car (ENTSEL "\n SELECT XLINE")))
  (SETQ XLINE_CORD (getpropertyvalue COPY_ENTITY "BasePoint"))
  (SETQ WPT1 (vlax-curve-getClosestPointTo TRACK_ENTITY_UPTRACK XLINE_CORD T))
  (SETQ WPT2 (vlax-curve-getClosestPointTo TRACK_ENTITY_UPTRACK (GETPOINT "\n PICK ANY POINT IN REQUIRED DIRECTION ") T))
 (SETQ DIRECTION (FIND_DIRECTION TRACK_ENTITY_UPTRACK WPT1 WPT2))
 (SETQ NUMBER (GETINT "\n ENTER KM COUNT"))
 (SETQ KM (GETSTRING "\n ENTER STARTING KM IN LOP"))
 (SETQ KM_STONE_LIST (INSERT_KM_STONE_GPS TRACK_ENTITY_UPTRACK WPT1 NUMBER DIRECTION))
 (SETQ I 0)
 (WHILE (< I (LENGTH KM_STONE_LIST))
  (MODIFY_ATTRIBUTES (NTH 0 (NTH I KM_STONE_LIST)) (LIST "KM" "LEFT_KM" "RIGHT_KM") (LIST (STRCAT "%%UCONT. KM:" KM) (STRCAT (ITOA (- (ATOI KM) 1)) "/1000.00" ) (STRCAT (ITOA (ATOI KM)) "/0000.00" )))
  (SETQ KM (ITOA (+ (ATOI KM) 1)))
  (SETQ I (+ I 1))
 )
)
(DEFUN INSERT_KM_STONE_GPS ( TRACK_ENTITY_UPTRACK STARTING_POINT NUMBER DIRECTION  / I FINAL_LIST ROTATION TEMP_DISTANCE ) 
(SETQ I 0 FINAL_LIST NIL ROTATION NIL TEMP_DISTANCE NIL)
  (WHILE (< I NUMBER)
    (SETQ ROTATION (GET_KM_ROTATION TRACK_ENTITY_UPTRACK STARTING_POINT))
    (COMMAND "INSERT" "KM_NEW" (POLAR STARTING_POINT (+ (/ PI 2) ROTATION) 52) "1" (* (/ 180 PI) ROTATION))
    (SETQ FINAL_LIST (CONS (LIST (ENTLAST) STARTING_POINT) FINAL_LIST))
      (SETQ TEMP_DISTANCE (VLAX-CURVE-GETDISTATPOINT TRACK_ENTITY_UPTRACK STARTING_POINT))
    (IF (= DIRECTION "POSITIVE")
      (SETQ TEMP_DISTANCE (- TEMP_DISTANCE 1000))
      (SETQ TEMP_DISTANCE (+ TEMP_DISTANCE 1000))
    )
   (SETQ STARTING_POINT (VLAX-CURVE-GETPOINTATDIST TRACK_ENTITY_UPTRACK TEMP_DISTANCE))

    (SETQ I (+ I 1))
  )
(REVERSE FINAL_LIST)
)
(DEFUN GET_KM_ROTATION (REFERENCE_POLYLINE POINT1 / MAIN_POINT ANGLE1 DERIVATIVE SLOPE)
  
  (SETQ TEMP_DISTANCE NIL MAIN_POINT NIL ANGLE1 NIL DERIVATIVE NIL SLOPE NIL)
  
  (SETQ ANGLE1 (VLAX-CURVE-GETPARAMATPOINT REFERENCE_POLYLINE POINT1))
  
  (SETQ DERIVATIVE (VLAX-CURVE-GETFIRSTDERIV REFERENCE_POLYLINE ANGLE1))
  
  (SETQ SLOPE (ANGLE '(0 0 0) DERIVATIVE))

  SLOPE

)
(DEFUN DFCC_KM_STONE_GPS ( / TRACK_ENTITY_UPTRACK WPT1 WPT2 DIRECTION NUMBER KM KM_STONE_LIST BLOCKS_LIST BLOCK_NAME_LIST KM_STONE_LIST I)
 (SETQ TRACK_ENTITY_UPTRACK (CAR(ENTSEL "\nSELECT REFERENCE TRACK ALIGNMENT:")))
 (SETQ WPT1 (GETPOINT "SELECT STARTING POINT ON REFERENCE TRACK ALIGNMENT"))
 (SETQ WPT2 (GETPOINT "\n PICK ANY POINT ON CURVE IN REQUIRED DIRECTION "))
 (SETQ DIRECTION (FIND_DIRECTION TRACK_ENTITY_UPTRACK WPT1 WPT2))
 (SETQ NUMBER (GETINT "\n ENTER KM COUNT"))
 (SETQ KM (GETSTRING "\n ENTER STARTING KM IN LOP"))
 (SETQ KM_STONE_LIST (INSERT_KM_STONE_GPS1 TRACK_ENTITY_UPTRACK WPT1 NUMBER DIRECTION))
 (SETQ I 0)
 (WHILE (< I (LENGTH KM_STONE_LIST))
  (MODIFY_ATTRIBUTES (NTH 0 (NTH I KM_STONE_LIST)) (LIST "KM" "LEFT_KM" "RIGHT_KM") (LIST (STRCAT "%%UKM:" KM) (STRCAT (ITOA (- (ATOI KM) 1)) "/1000.00" ) (STRCAT (ITOA (ATOI KM)) "/0000.00" )))
  (SETQ KM (ITOA (+ (ATOI KM) 1)))
  (SETQ I (+ I 1))
 )
)
(DEFUN INSERT_KM_STONE_GPS1 ( TRACK_ENTITY_UPTRACK STARTING_POINT NUMBER DIRECTION  / I FINAL_LIST ROTATION TEMP_DISTANCE ) 
(SETQ I 0 FINAL_LIST NIL ROTATION NIL TEMP_DISTANCE NIL)
  (WHILE (< I NUMBER)
    (SETQ ROTATION (GET_KM_ROTATION TRACK_ENTITY_UPTRACK STARTING_POINT))
    (COMMAND "INSERT" "DFCC_KM_NEW" (POLAR STARTING_POINT (+ (/ PI 2) ROTATION) 52) "1" (* (/ 180 PI) ROTATION))
    (SETQ FINAL_LIST (CONS (LIST (ENTLAST) STARTING_POINT) FINAL_LIST))
      (SETQ TEMP_DISTANCE (VLAX-CURVE-GETDISTATPOINT TRACK_ENTITY_UPTRACK STARTING_POINT))
    (IF (= DIRECTION "POSITIVE")
      (SETQ TEMP_DISTANCE (- TEMP_DISTANCE 1000))
      (SETQ TEMP_DISTANCE (+ TEMP_DISTANCE 1000))
    )
   (SETQ STARTING_POINT (VLAX-CURVE-GETPOINTATDIST TRACK_ENTITY_UPTRACK TEMP_DISTANCE))

    (SETQ I (+ I 1))
  )
(REVERSE FINAL_LIST)
)
(DEFUN C:MATCH_POSITION (ENTNAME ENT_LIST ATTRIBUTE_TAG / ENTNAME SSSET ENT_LIST ENT_INFO MAST_NUMBER MAST_NUMBER_X MAST_NUMBER_Y FDN_REFERENCE FDN_REFERENCE_X FDN_REFERENCE_Y RD_REFERENCE RD_REFERENCE_X RD_REFERENCE_Y TC_REFERENCE TC_REFERENCE_X TC_REFERENCE_Y SPAN_REFERENCE_X SPAN_REFERENCE_Y BS_PT VALUES VALUES1 VALUES2 VALUES3 VALUES4 VALUES5 POINT POINT1 POINT2 POINT3 POINT4 POINT5 VISIBILITY_SPAN VISIBILITY_TC VISIBILITY_FDN VISIBILITY_RD I BASE_POINT TEMP_SPAN) 

  (COMMAND "UCS" "W")
  
  (SETQ ENT_LIST (LIST (CAR (ENTSEL "SELECT MAST"))))

  (SETQ DFCC_CTN_CHAINAGE_REFERENCE (GET_TEXT_ALIGNMENT_POINT (LIST ENTNAME) ATTRIBUTE_TAG 0))
  (SETQ DFCC_CTN_CHAINAGE_REFERENCE_X (- (NTH 0 (NTH 1 (NTH 0 DFCC_CTN_CHAINAGE_REFERENCE))) (NTH 0 (CDR (ASSOC 10 (ENTGET ENTNAME))))))
  (SETQ DFCC_CTN_CHAINAGE_REFERENCE_Y (- (NTH 1 (NTH 1 (NTH 0 DFCC_CTN_CHAINAGE_REFERENCE))) (NTH 1 (CDR (ASSOC 10 (ENTGET ENTNAME))))))

  (SETQ REFERENCE_LIST1 (LIST (LIST DFCC_CTN_CHAINAGE_REFERENCE_X DFCC_CTN_CHAINAGE_REFERENCE_Y 0.0)))
  ;(SETQ BS_PT (CDR (ASSOC 10 (ENTGET ENTNAME))))

  (SETQ BASE_ROTATION (VLAX-GET-PROPERTY (VLAX-ENAME->VLA-OBJECT ENTNAME) 'ROTATION))

  (SETQ I 0 BASE_POINT NIL ROTATION NIL TEMP_IMPLANTATION NIL TEMP_POINT_LIST NIL )
  (WHILE (< I (LENGTH ENT_LIST))
    
    (SETQ BASE_POINT (CDR (ASSOC 10 (ENTGET (NTH I ENT_LIST)))))
    (SETQ ROTATION (VLAX-GET-PROPERTY (VLAX-ENAME->VLA-OBJECT (NTH I ENT_LIST)) 'ROTATION))
    (SETQ TEMP_IMPLANTATION (ATOF (NTH 0 (SINGLE_ELE_LIST (EXTRACT_ATTRIBUTES (NTH I ENT_LIST) (LIST "IMPLANTATION1" ) 1) 1))))
    
    (SETQ TEMP_POINT_LIST1 (TRANSFORM_ADJ REFERENCE_LIST1 BASE_POINT (-  ROTATION BASE_ROTATION) (- 3.00 3.00)))

    (CHANGE_TEXT_ALIGNMENT_POINT (NTH I ENT_LIST) (LIST ATTRIBUTE_TAG) (LIST (NTH 0 TEMP_POINT_LIST1)))

    (SETQ I (+ I 1))
  )
  (COMMAND "UCS" "P")
  )
  
  ;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
;                                                       view port creation programs                                                                                  ;
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;





(defun c:create_viewport ( / shape corners lowest_point corners lowest_point active_document insertion_point point point2 rectangle_length rectangle_width viewport )
(command "ucs" "w")
(setq base_points (list (getpoint " n/ select first base point of a rectangle") (getpoint " n/ select second base point of a rectangle")))
(setq ortho_point (getpoint " n/ select a point perpendicular to base line from second base point"))
(command "ucs" "p")
(setq active_document (vla-get-activedocument (vlax-get-acad-object)))
(vlax-put-property active_document "activespace" acpaperspace)
(setq insertion_point (getpoint))
(setq leng (distance (nth 0 base_points) (nth 1 base_points)))
(setq width (distance (nth 1 base_points) ortho_point))
;(setq diag (distance (nth 0 base_points) ortho_point))

(setq viewport (vlax-invoke-method (vlax-get-property active_document "paperspace") "addpviewport" (vlax-3d-point insertion_point) (* 2 leng) (* width 2)))
(vlax-invoke-method viewport "display" :vlax-true)
(command "_mspace")
(if (/= (getvar "cvport") (cdr (assoc 69 (entget (vlax-vla-object->ename viewport)))))
(setvar "cvport" (cdr (assoc 69 (entget (vlax-vla-object->ename viewport)))))
)
(alignspace (nth 0 base_points) (nth 1 base_points) (list 0 0 0) (polar (list 0 0 0) 0 10))
(command "zoom" "w" (nth 0 base_points) ortho_point)
)




(defun chainage_viewports (entname active_document insertion_point / main_points leng width viewport )

(setq main_points (get_box_points_entity entname))

(setq leng (distance (nth 0 main_points) (nth 1 main_points)))
(setq width (distance (nth 1 main_points) (nth 2 main_points)))
;(setq diag (distance (nth 0 base_points) ortho_point))

(setq viewport (vlax-invoke-method (vlax-get-property active_document "paperspace") "addpviewport" (vlax-3d-point insertion_point) (* 2 leng) (* width 2)))
(vlax-invoke-method viewport "display" :vlax-true)
(command "_mspace")
(if (/= (getvar "cvport") (cdr (assoc 69 (entget (vlax-vla-object->ename viewport)))))
(setvar "cvport" (cdr (assoc 69 (entget (vlax-vla-object->ename viewport)))))
)
(alignspace (nth 0 main_points) (nth 1 main_points) (list 0 0 0) (polar (list 0 0 0) 0 10))
(command "zoom" "w" (nth 0 main_points) (nth 2 main_points))
(command "_pspace")
)

(defun get_box_points_entity (block / base_point rotation rect_points sort_y_points sort_x_points ortho_point base_points ortho_point )
(setq base_point (cdr (assoc 10 (entget block))))
(setq rotation (vlax-get-property (vlax-ename->vla-object block) "rotation"))
(setq rect_points (add_lists (build_list (filter_list (list "ohe-rect-location border") (block_ename1 block) 0) (list 3 4)) (n_ele_list 0.0 4)))
(setq sort_y_points (sort_fun rect_points 0 1))
(setq sort_x_points (sort_fun rect_points 0 0))
(setq base_points (sort_fun (list (nth 0 sort_y_points) (nth 1 sort_y_points)) 0 0))
(setq ortho_point (nth 1 (sort_fun (list (nth 2 sort_x_points) (nth 3 sort_x_points)) 0 1)))
(setq base_points (transform base_points base_point  rotation))
(setq ortho_point (transform (list ortho_point) base_point rotation))
(append base_points ortho_point)
)


(defun c:get_chainage_viewports ( / active_document insertion_point i )
  (if (= (vl-position (getvar "cvport") (list 0 1)) nil)
  (progn
  (command "ucs" "w")
  (prompt "n/select masts : ")
  (setq masts (ssget))
  (setq masts (form_ssset masts))
  (command "ucs" "p")
  (command "_pspace")
  (setq active_document (vla-get-activedocument (vlax-get-acad-object)))
  (setq insertion_point (getpoint))
  (setq i 0)
  (while (< i (length masts))
    (chainage_viewports (nth i masts) active_document insertion_point)
    (setq insertion_point (list (+ (car insertion_point) 54) (cadr insertion_point) 0.0))
    (setq i (+ i 1))
  )
  )
  (progn (alert "this command is not allowed in model space and paper space. activate view port to run this command")
  )
  )
)
  
(defun get_box_points ( / block base_point rotation rect_points sort_y_points sort_x_points base_points ortho_point )
(setq block (car(entsel)))
(setq base_point (cdr (assoc 10 (entget block))))
(setq rotation (vlax-get-property (vlax-ename->vla-object block) "rotation"))
(setq rect_points (add_lists (build_list (filter_list (list "ohe-rect-location border") (block_ename1 block) 0) (list 3 4)) (n_ele_list 0.0 4)))
(setq sort_y_points (sort_fun rect_points 0 1))
(setq sort_x_points (sort_fun rect_points 0 0))
(setq base_points (sort_fun (list (nth 0 sort_y_points) (nth 1 sort_y_points)) 0 0))
(setq ortho_point (nth 1 (sort_fun (list (nth 2 sort_x_points) (nth 3 sort_x_points)) 0 1)))
(setq base_points (transform base_points base_point  rotation))
(setq ortho_point (transform (list ortho_point) base_point rotation))
(append base_points ortho_point)
)


(defun transform (list1 base_point rotation / i x y final_list)
  (setq i 0 x nil y nil final_list nil)
  (while (< i (length list1))
    (setq temp_point (polar base_point (+ (angle (list 0 0 0) (nth i list1)) rotation) (distance (list 0 0 0) (nth i list1))))
    (setq final_list (cons temp_point final_list))
    (setq i (+ i 1))
  )
(reverse final_list)
)

    
(defun get_rectangle_corners (entity  / list1 x )
  (setq list1 (sort_fun (build_list (filter_list (list 10) (entget entity) 0) (list 1 2)) 0 1))
  (setq x
  (list
  (list (vlax-curve-getdistatpoint entity (nth 0 list1)) (nth 0 list1))
  (list (vlax-curve-getdistatpoint entity (nth 1 list1)) (nth 1 list1))
  (list (vlax-curve-getdistatpoint entity (nth 2 list1)) (nth 2 list1))
  (list (vlax-curve-getdistatpoint entity (nth 3 list1)) (nth 3 list1))
  )
  )
  
  (setq x (sort_fun x 0 0))
  (setq x (list (nth 0 x) (nth 2 x)))
  (list (single_ele_list x 1) (nth 0 list1))
)


(defun get_point_direction (entity point / dist point1 point2) 
(setq dist (vlax-curve-getdistatpoint entity point))
(setq point1 (vlax-curve-getpointatdist entity (+ dist 10)))
(setq point2 (vlax-curve-getpointatdist entity (- dist 10)))
(nth 1 (sort_fun (list point1 point2) 0 0))
)




(defun sub_ent_data_collect (blockename	filter_list
			     dfx1	dfx2	   /
			     bs_pt	ename	   sub_ent_list
			     i		temp_ele   list2
			     j		flag	   list2
			    )
  (setq bs_pt (cdr (assoc 10 (entget blockename))))
  (if (setq
	ename (tblobjname "block" (cdr (assoc 2 (entget blockename))))
      )
    (reverse
      (while (setq ename (entnext ename))
	(setq sub_ent_list (cons ename sub_ent_list))
      )
    )
  )


  (setq i 0)
  (setq temp_ele nil)
  (setq list2 nil)
  (while (< i (length sub_ent_list))
    (setq temp_ele (entget (nth i sub_ent_list)))
    (setq j 0)
    (setq flag 1)
    (while (< j (length filter_list))
      (if (= (vl-position (nth j filter_list) temp_ele) nil)
	(progn (setq j (length filter_list)) (setq flag 0))
      )
      (setq j (+ j 1))
    )
    (if	(= flag 1)
      (setq list2 (cons	(sum_list1 bs_pt
				   (list (cdr (assoc dfx1 temp_ele))
					 (cdr (assoc dfx2 temp_ele))
				   )
			)
			list2
		  )
      )
    )
    (setq i (+ i 1))
  )
  (reverse list2)
)
(DEFUN C:BTB_ANC(/ BLOCKS_LIST BLOCK_NAME_LIST ANCHOR_LIST ANCHOR MAST MAST_FLIP)
(SETQ BLOCKS_LIST (FORM_SSSET (SSGET "X" (LIST (CONS 0 "INSERT")))))
(SETQ BLOCK_NAME_LIST (EXTRACT_ENTITY_INFO2 BLOCKS_LIST))
(SETQ MAST_TTC (YARD_DATA_COLLECT_GPS BLOCKS_LIST '("SINGLE_CANT_MAST" "DOUBLE_CANT_MAST" "TRIPLE_CANT_MAST" "TTC" "SS0" "SS1" "SS2" "SS3" "SS4") 1 3))
(SETQ ANCHOR_LIST (YARD_DATA_COLLECT_GPS BLOCKS_LIST '("BTB_ANC")  1 3))
(IF (/= ANCHOR_LIST NIL) (SETQ ANCHOR_STRUCTURE_MAP_DATA (DATA_TO_STRUCTURE_MAP_SECTIONING ANCHOR_LIST MAST_TTC 1 1)) (SETQ ANCHOR_STRUCTURE_MAP_DATA NIL))
(SETQ I 0)
(WHILE (< I (LENGTH ANCHOR_STRUCTURE_MAP_DATA))
  (SETQ ANCHOR (NTH 0 (NTH I ANCHOR_STRUCTURE_MAP_DATA)))
  (SETQ MAST (NTH 1 (NTH I ANCHOR_STRUCTURE_MAP_DATA)))
  (SETQ MAST_FLIP (NTH 1 (NTH 0 (GET_DYNAMIC_PROPERTIES MAST (LIST "STF1")))))
 
  (IF (= MAST_FLIP 0)
   (INSERT_DYNAMIC_PROPERTIES ANCHOR (LIST "A1" "D1" "D2" "A2")  (LIST 2.35619 4.50 4.50 2.35619 ))
   (INSERT_DYNAMIC_PROPERTIES ANCHOR (LIST "A1" "D1" "D2" "A2")  (LIST 0.785398 4.50 4.50 3.9269908 ))
   )
  (SETQ I (+ I 1))
 )
 )
 ;;;;;;;;;;;;;;;;;;;;;;;;;;;;;;;;;;;;;;;;;;;;
 (DEFUN DATA_TO_STRUCTURE_MAP_SECTIONING (LIST1 LIST2 K Q  / I TEMP_ELE TEMP_ELE1 LIST3)
(SETQ I 0)
(SETQ TEMP_ELE NIL)
(SETQ TEMP_ELE1 NIL)
(SETQ LIST3 NIL)
(WHILE (< I (LENGTH LIST1))
  (SETQ TEMP_ELE1 (MAP_NEAREST1 LIST2 (NTH K (NTH I LIST1)) Q ))
  (SETQ TEMP_ELE (APPEND (LIST (NTH 0 (NTH I LIST1))) TEMP_ELE1 ))
  (SETQ LIST3 (CONS TEMP_ELE LIST3))
  ;(SETQ LIST2 (VL-REMOVE TEMP_ELE1 LIST2))
  (SETQ I (+ I 1))
  )
LIST3
)
;;;;;;;;;;;;;;;;;;;;;;;;;;;;;;;;;;;;;;;;;;;;;;;
(DEFUN MAP_NEAREST1 (LIST1 PT K / I TEMP_SET LIST2)
  (SETQ I 0)
  (SETQ TEMP_SET NIL)
  (SETQ LIST2 NIL)
  (WHILE (< I (LENGTH LIST1))
    (IF	(NOT (ATOM (NTH K (NTH I LIST1))))
      (PROGN (SETQ TEMP_SET
		    (LIST
		      (ABS (DISTANCE (NTH K (NTH I LIST1)) PT))
		      (NTH I LIST1)
		    )
	     )
	     (SETQ LIST2 (CONS TEMP_SET LIST2))
      )
      (PROGN (SETQ TEMP_SET (LIST (ABS (DISTANCE (NTH I LIST1) PT))
				  (NTH I LIST1)
			    )
	     )
	     (SETQ LIST2 (CONS TEMP_SET LIST2))
      )
    )
    (SETQ I (+ I 1))
  )
  (NTH 1 (NTH 0 (SORT_FUN LIST2 0 0)))
)

;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
(defun *error* (errmsg)
	 (princ "\nAn error has occurred in the programme. ")
	 (terpri)
	 (prompt errmsg)
	 (princ)
	)













	





	;;;;;INSTANT CODES
(defun C:1_UPDATE_FDN_CORDINATES () ;TO UPDATE THE ACTUAL CORDINATES THAT WE FILL IN CSD
(WHILE (> 1 0)
(setq BLOCK (entsel "Select the BLOCK : "))
(setq PORTAL_TYPE (SUBSTR (GETPROPERTYVALUE (CAR BLOCK) "MAST_TYPE1") 1 2))
(IF (= PORTAL_TYPE "WN")
(PROGN
(setq UR_W 0.275)
)(setq UR_W 0.3)
)
(setq CS_PORTAL (round (getpropertyvalue (car BLOCK) "AcDbDynBlockPropertySTL1") 0.05))
(setq BLOCK_CORD (OBJECT_CORDINATES BLOCK))
(setq ROT 7.78) ;;;; CHANGE HERE
(setq ROT_old (/ (* (getpropertyvalue (car BLOCK) "Rotation") 180) pi))
(setq ANG1 (+ 270 ROT))
(setq ANG2 (+ 90 ROT))
(setq FDN_CORD1 (POLAR BLOCK_CORD (/ (* ANG1 pi) 180) UR_W))
(setq FDN_CORD2 (POLAR BLOCK_CORD (/ (* ANG2 pi) 180) (+ UR_W CS_PORTAL)))
(setq ANG1_old (+ 270 ROT_old))
(setq ANG2_old (+ 90 ROT_old))
(setq FDN_CORD1_old (POLAR BLOCK_CORD (/ (* ANG1_old pi) 180) UR_W))
(setq FDN_CORD2_old (POLAR BLOCK_CORD (/ (* ANG2_old pi) 180) (+ UR_W CS_PORTAL)))
(ssget "_C" FDN_CORD1_old FDN_CORD1_old '((0 . "POINT")))
(command "_.erase" (ssget "_C" FDN_CORD1_old FDN_CORD1_old '((0 . "POINT"))) "")
(ssget "_C" FDN_CORD2_old FDN_CORD2_old '((0 . "POINT")))
(command "_.erase" (ssget "_C" FDN_CORD2_old FDN_CORD2_old '((0 . "POINT"))) "")
(command "POINT" fdn_cord1)
(command "POINT" fdn_cord2)
(MODIFY_ATTRIBUTES (car BLOCK) (LIST "DUMMY_VARIABLE5" "DUMMY_VARIABLE1") (LIST (STRCAT "(" (RTOS (CAR FDN_CORD1) 2 2) " , " (RTOS (NTH 1 FDN_CORD1) 2 2) ")") (STRCAT "(" (RTOS (CAR FDN_CORD2) 2 2) " , " (RTOS (NTH 1 FDN_CORD2) 2 2) ")")))
(setpropertyvalue (CAR BLOCK) "Color" "6")
(setq temp_portal BLOCK)
(setq DV1 (assoc "DUMMY_VARIABLE1" (GET_ATTRIBUTES (CAR temp_portal))))
(setq DV5 (assoc "DUMMY_VARIABLE5" (GET_ATTRIBUTES (CAR temp_portal))))
(setq COR1 (LIST (NTH 0 (READ (NTH 1 DV1))) (NTH 2 (READ (NTH 1 DV1))) 0.0))
(setq COR2 (LIST (NTH 0 (READ (NTH 1 DV5))) (NTH 2 (READ (NTH 1 DV5))) 0.0))
(setq Mno1 (NTH 1 (assoc "MAST_NUMBER1" (GET_ATTRIBUTES (CAR temp_portal)))))
(setq Mno2 (NTH 1 (assoc "MAST_NUMBER2" (GET_ATTRIBUTES (CAR temp_portal)))))
(COMMAND "MTEXT" COR1 COR1 Mno1 "")
(setpropertyvalue (entlast) "Color" "3")
(COMMAND "MTEXT" COR2 COR2 Mno2 "")
(setpropertyvalue (entlast) "Color" "3")
)
)
(DEFUN C:2_PUT_MAST_NUMBER ()

(setq temp_portal (entsel "select Portal: "))
(setq DV1 (assoc "DUMMY_VARIABLE1" (GET_ATTRIBUTES (CAR temp_portal))))
(setq DV5 (assoc "DUMMY_VARIABLE5" (GET_ATTRIBUTES (CAR temp_portal))))
(setq COR1 (LIST (NTH 0 (READ (NTH 1 DV1))) (NTH 2 (READ (NTH 1 DV1))) 0.0))
(setq COR2 (LIST (NTH 0 (READ (NTH 1 DV5))) (NTH 2 (READ (NTH 1 DV5))) 0.0))
(setq Mno1 (NTH 1 (assoc "MAST_NUMBER1" (GET_ATTRIBUTES (CAR temp_portal)))))
(setq Mno2 (NTH 1 (assoc "MAST_NUMBER2" (GET_ATTRIBUTES (CAR temp_portal)))))
(COMMAND "MTEXT" COR1 COR1 Mno1 "")
(setpropertyvalue (entlast) "Color" "3")
(COMMAND "MTEXT" COR2 COR2 Mno2 "")
(setpropertyvalue (entlast) "Color" "3")
)
