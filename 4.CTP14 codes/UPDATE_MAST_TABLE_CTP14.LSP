(DEFUN C:UPDATE_MAST_TABLE_CTP14(/ WPT1 WPT2 WPT3 WPT4 START_KM BLOCKS_LIST MAST_TTC ENT_LIST TEMP_CHAINAGE TBL TEMP_KM_CHAINAGE TEMP_MAST_TYPE MAST175 MAST200 MAST225 MAST250 MASTBRIDGE)
  (SETQ WPT1 (GETPOINT "\n ENTER 1ST POINT OF POLYGON"))
  (SETQ WPT2 (GETPOINT "\n ENTER 2ND POINT OF POLYGON"))
  (SETQ WPT3 (GETPOINT "\n ENTER 3RD POINT OF POLYGON"))
  (SETQ WPT4 (GETPOINT "\n ENTER 4TH POINT OF POLYGON"))
   ;(SETQ BLOCKS_LIST (FORM_SSSET (SSGET "X" (LIST (CONS 0 "INSERT")))))
   (SETQ BLOCKS_LIST (FORM_SSSET (SSGET "WP" (LIST WPT1 WPT2 WPT3 WPT4) (LIST (CONS 0 "INSERT")))))
  (SETQ START_KM (GETINT "\n ENTER STARTING KM:"))
  (SETQ TBL NIL)
  (SETQ TBL (CAR (ENTSEL"\n select the refernce mast table"))) 
  (SETQ TBL (VLAX-ENAME->VLA-OBJECT TBL))
 
  (SETQ MAST_TTC (YARD_DATA_COLLECT_GPS BLOCKS_LIST '("SINGLE_CANT_MAST" "DOUBLE_CANT_MAST" "TRIPLE_CANT_MAST" "TTC" "SS0" "SS1" "SS2" "SS3" "SS4") 1 3))
  (SETQ ENT_LIST (SINGLE_ELE_LIST MAST_TTC 0))
  (SETQ A175 0 A200 0 A225 0 A250 0 ABRIDGE 0)
  (SETQ B175 0 B200 0 B225 0 B250 0 BBRIDGE 0)
  (SETQ C175 0 C200 0 C225 0 C250 0 CBRIDGE 0)
  (SETQ D175 0 D200 0 D225 0 D250 0 DBRIDGE 0)
  (SETQ E175 0 E200 0 E225 0 E250 0 EBRIDGE 0)
  (SETQ I 0)
  (WHILE (< I  (LENGTH ENT_LIST))
         (SETQ TEMP_CHAINAGE (NTH 0 (SINGLE_ELE_LIST (EXTRACT_ATTRIBUTES (NTH I ENT_LIST) (LIST "CHAINAGE2" ) 1) 1)))
		 (SETQ TEMP_KM_CHAINAGE (SUBSTR TEMP_CHAINAGE 1 (VL-STRING-SEARCH "/" TEMP_CHAINAGE)))
		 (SETQ TEMP_KM_CHAINAGE (ATOI TEMP_KM_CHAINAGE))
		 (SETQ TEMP_MAST_TYPE (NTH 0 (SINGLE_ELE_LIST (EXTRACT_ATTRIBUTES (NTH I ENT_LIST) (LIST "MAST_TYPE1" ) 1) 1)))
		 
		 
		 
		 
		 (COND  ((AND ( >= TEMP_KM_CHAINAGE START_KM) (< TEMP_KM_CHAINAGE (+ 1 START_KM))) 
		          (COND ((= TEMP_MAST_TYPE "B-175(S)")(SETQ A175 (+ A175 1)))
				        ((= TEMP_MAST_TYPE "B-200(S)")(SETQ A200 (+ A200 1)))
						((= TEMP_MAST_TYPE "B-225(S)")(SETQ A225 (+ A225 1)))
						((= TEMP_MAST_TYPE "B-250(S)")(SETQ A250 (+ A250 1)))
						((= TEMP_MAST_TYPE "BRIDGE MAST")(SETQ ABRIDGE (+ ABRIDGE 1)))
				    )
				)
				
				((AND ( >= TEMP_KM_CHAINAGE (+ 1 START_KM)) (< TEMP_KM_CHAINAGE (+ 2 START_KM))) 
		          (COND ((= TEMP_MAST_TYPE "B-175(S)")(SETQ B175 (+ B175 1)))
				        ((= TEMP_MAST_TYPE "B-200(S)")(SETQ B200 (+ B200 1)))
						((= TEMP_MAST_TYPE "B-225(S)")(SETQ B225 (+ B225 1)))
						((= TEMP_MAST_TYPE "B-250(S)")(SETQ B250 (+ B250 1)))
						((= TEMP_MAST_TYPE "BRIDGE MAST")(SETQ BBRIDGE (+ BBRIDGE 1)))
				    )
				)
				((AND ( >= TEMP_KM_CHAINAGE (+ 2 START_KM)) (< TEMP_KM_CHAINAGE (+ 3 START_KM))) 
		          (COND ((= TEMP_MAST_TYPE "B-175(S)")(SETQ C175 (+ C175 1)))
				        ((= TEMP_MAST_TYPE "B-200(S)")(SETQ C200 (+ C200 1)))
						((= TEMP_MAST_TYPE "B-225(S)")(SETQ C225 (+ C225 1)))
						((= TEMP_MAST_TYPE "B-250(S)")(SETQ C250 (+ C250 1)))
						((= TEMP_MAST_TYPE "BRIDGE MAST")(SETQ CBRIDGE (+ CBRIDGE 1)))
				    )
				)
				((AND ( >= TEMP_KM_CHAINAGE (+ 3 START_KM)) (< TEMP_KM_CHAINAGE (+ 4 START_KM))) 
		          (COND ((= TEMP_MAST_TYPE "B-175(S)")(SETQ D175 (+ D175 1)))
				        ((= TEMP_MAST_TYPE "B-200(S)")(SETQ D200 (+ D200 1)))
						((= TEMP_MAST_TYPE "B-225(S)")(SETQ D225 (+ D225 1)))
						((= TEMP_MAST_TYPE "B-250(S)")(SETQ D250 (+ D250 1)))
						((= TEMP_MAST_TYPE "BRIDGE MAST")(SETQ DBRIDGE (+ DBRIDGE 1)))
				    )
				)
				((AND ( >= TEMP_KM_CHAINAGE (+ 4 START_KM)) (< TEMP_KM_CHAINAGE (+ 5 START_KM))) 
		          (COND ((= TEMP_MAST_TYPE "B-175(S)")(SETQ E175 (+ E175 1)))
				        ((= TEMP_MAST_TYPE "B-200(S)")(SETQ E200 (+ E200 1)))
						((= TEMP_MAST_TYPE "B-225(S)")(SETQ E225 (+ E225 1)))
						((= TEMP_MAST_TYPE "B-250(S)")(SETQ E250 (+ E250 1)))
						((= TEMP_MAST_TYPE "BRIDGE MAST")(SETQ EBRIDGE (+ EBRIDGE 1)))
				    )
				)
				      
					  
					  
			)
			(SETQ I (+ I 1))
			
	)
	(SETQ MAST175 (LIST A175 B175 C175 D175 ))
	(SETQ MAST200 (LIST A200 B200 C200 D200 ))
	(SETQ MAST225 (LIST A225 B225 C225 D225 ))
	(SETQ MAST250 (LIST A250 B250 C250 D250 ))
	(SETQ MASTBRIDGE (LIST ABRIDGE BBRIDGE CBRIDGE DBRIDGE ))
	 
	(SETQ J 0)
	(WHILE (< J 4)
	 (VLAX-INVOKE-METHOD
	    TBL
	    "SETCELLVALUE"
	    (+ J 3)
	    0
	    (+ J START_KM)
	  )
	
	 (SETQ J (+ J 1))
	
	)
	 ;(SETQ J 0)
	;(WHILE (< J 4)
	; (VLAX-INVOKE-METHOD
    ;    TBL
	;    "SETCELLVALUE"
	;    (+ J 3)
	;    1
	 ;   (NTH J MAST175)
	 ; )
	
	; (SETQ J (+ J 1))
	
	;)
	 (SETQ J 0)
	(WHILE (< J 4)
	 (VLAX-INVOKE-METHOD
	    TBL
	    "SETCELLVALUE"
	    (+ J 3)
	    1
	    (NTH J MAST175)
	  )
	
	 (SETQ J (+ J 1))
	
	)
	 (SETQ J 0)
	(WHILE (< J 4)
	 (VLAX-INVOKE-METHOD
	    TBL
	    "SETCELLVALUE"
	    (+ J 3)
	    2
	    (NTH J MAST200)
	  )
	
	 (SETQ J (+ J 1))
	
	)
	
	 (SETQ J 0)
	(WHILE (< J 4)
	 (VLAX-INVOKE-METHOD
	    TBL
	    "SETCELLVALUE"
	    (+ J 3)
	    3
	    (NTH J MAST225)
	  )
	
	 (SETQ J (+ J 1))
	
	)
	
	
	(SETQ J 0)
	(WHILE (< J 4)
	 (VLAX-INVOKE-METHOD
	    TBL
	    "SETCELLVALUE"
	    (+ J 3)
	    4
	    (NTH J MAST250)
	  )
	
	 (SETQ J (+ J 1))
	
	)
	
	(SETQ J 0)
	(WHILE (< J 4)
	 (VLAX-INVOKE-METHOD
	    TBL
	    "SETCELLVALUE"
	    (+ J 3)
	    5
	    (NTH J MASTBRIDGE)
	  )
	
	 (SETQ J (+ J 1))
	
	)
	
	)



(DEFUN FORM_SSSET (SSSET / I TEMP_ELE LIST1)
  (SETQ I 0)
  (SETQ TEMP_ELE NIL)
  (SETQ LIST1 NIL_)
  (WHILE (< I (SSLENGTH SSSET))
    (SETQ TEMP_ELE (SSNAME SSSET I))
    (SETQ LIST1 (CONS TEMP_ELE LIST1))
    (SETQ I (+ I 1))
  )
  (REVERSE LIST1)
)
