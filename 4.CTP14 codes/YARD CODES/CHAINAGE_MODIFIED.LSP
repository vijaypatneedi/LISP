(defun C:chainage_modified( / WPT1 WPT2 KM_SORTED DIST_T Q DIST_FIRST TRACK_ENTITY_DNTRACK BLOCKS_LIST BLOCK_NAME_LIST KM_STONE_LIST KM_STONE_COORDINATES KM_STONE_DISTANCE KM_STONE_SORTED MAST_TTC_DIR I J MAST MAST_POINT MAST_WITH_POINT MAST_WITH_DIST TEMP_DFCC_KM_CHAINAGE M_NUM TEMP_CHAIN )
  (SETQ WPT1 (GETPOINT "\nSELECT POINT1:"))
  (SETQ WPT2 (GETPOINT "\nSELECT POINT2:"))
  (SETQ TRACK_ENTITY_DNTRACK POLYLINE_ENTITY_FOR_DISTANCE_V)
   (SETQ BLOCKS_LIST (FORM_SSSET (SSGET "W" WPT1 WPT2 (LIST (CONS 0 "INSERT")))))
  (SETQ BLOCK_NAME_LIST (EXTRACT_ENTITY_INFO2 BLOCKS_LIST))
  (SETQ KM_STONE_LIST (FILTER_LIST (LIST "KM_NEW") BLOCK_NAME_LIST 1))
  (SETQ KM_STONE_LIST (SORT_FUN (ENTITY_DFX (SINGLE_ELE_LIST KM_STONE_LIST 0) 10 -1) 1 0))
  (SETQ KM_STONE_COORDINATES (COMBINE_LIST_ELEMENTS (GET_PROJECTION_FROM_POINT_LIST_FINAL TRACK_ENTITY_DNTRACK (BUILD_LIST KM_STONE_LIST (LIST 0 1)) 1)))
 
  (SETQ KM_STONE_COORDINATES (BUILD_LIST KM_STONE_COORDINATES (LIST 0 2)))
  (SETQ KM_STONE_DISTANCE (DISTANCE_LINE KM_STONE_COORDINATES))
  
  (SETQ KM_STONE_SORTED (SORT_FUN KM_STONE_DISTANCE 1 1))
  (SETQ DIST_FIRST (NTH 1 (NTH 0 KM_STONE_SORTED)))
  (SETQ KM_SORTED NIL Q 0)
  (while (< q (length KM_STONE_SORTED))
    ;(SETQ DIST_T (NTH 1 (NTH Q KM_STONE_SORTED)))
	(SETQ DIST_T (+ (* Q 1000) DIST_FIRST))
	(SETQ KM_SORTED (CONS (LIST (NTH 0 (NTH Q KM_STONE_SORTED)) DIST_T) KM_SORTED))
    (SETQ Q (+ Q 1))
  
  
  )
  (SETQ KM_SORTED (REVERSE KM_SORTED))
  (SETQ KM_STONE_SORTED KM_SORTED)

 ;(SETQ KM_STONE_COORDINATES (SORT_ENTITIES_ALONG_CURVE TRACK_ENTITY_DNTRACK KM_STONE_COORDINATES (LIST 1 STARTING_POINT) 2 1))
  ;(SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
   
   (SETQ I 1000)
   
   (WHILE (/= I 100)
     (SETQ J 0)
    (SETQ MAST (CAR (ENTSEL "\nSELECT MAST")))
	(SETQ MAST_POINT (CADR (CAR (FILTER_LIST (LIST 3) (YARD_STRUCTURE_INFO_GPS MAST) 0))))
	(SETQ MAST_WITH_POINT (LIST MAST MAST_POINT))
	(SETQ MAST_WITH_DIST (DISTANCE_LINE (LIST MAST_WITH_POINT)))
	
	(WHILE (< J (LENGTH KM_STONE_SORTED))
	
	(IF (> (CADR (CAR MAST_WITH_DIST)) (CADR (NTH J KM_STONE_SORTED)))
	 (PROGN
	 (SETQ KM_NUM (NTH 1 (NTH 0 (FILTER_LIST (LIST "KM") (GET_ATTRIBUTES (NTH 0 (NTH J KM_STONE_SORTED))) 0 ))))
	 
	 (IF (/= (VL-STRING-SEARCH ":" KM_NUM) NIL)
	 (SETQ TEMP_DFCC_KM_CHAINAGE (SUBSTR KM_NUM (+ 2 (VL-STRING-SEARCH ":" KM_NUM))))
	  (SETQ TEMP_DFCC_KM_CHAINAGE "0.00")
	 )
	 (SETQ M_NUM (- (CADR (CAR MAST_WITH_DIST)) (CADR (NTH J KM_STONE_SORTED))))
	 
	 (SETQ M_NUM (ROUNDM M_NUM 0.05))
	 (SETQ TEMP_CHAIN (STRCAT TEMP_DFCC_KM_CHAINAGE "/" (RTOS M_NUM 2 2)))
	 
	  (MODIFY_ATTRIBUTES MAST (LIST "CHAINAGE1" "CHAINAGE2") (LIST TEMP_CHAIN TEMP_CHAIN))
	  
	  ;(SETQ J (LENGTH KM_STONE_SORTED))
	  ;(SETQ J (+ J 1))
	  
	  )
	  )
	
	
	
	(SETQ J (+ J 1))
	)
	
	(SETQ I (- I 1))
	)
	
)





(DEFUN DISTANCE_LINE (ENT_LIST / FINAL_LIST I TEMP_DISTANCE1 P1 ent1)
(setq ent1 (vlax-ename->vla-object POLYLINE_ENTITY_FOR_DISTANCE_V))
(SETQ I 0 FINAL_LIST NIL)
(WHILE (< I (LENGTH ENT_LIST))
  (SETQ P1 (NTH 1 (NTH I ENT_LIST)))
  (SETQ TEMP_DISTANCE1 (VLAX-CURVE-GETDISTATPOINT ent1 (vlax-curve-getclosestpointto ent1 P1)))
  (SETQ FINAL_LIST (CONS (LIST (NTH 0 (NTH I ENT_LIST)) TEMP_DISTANCE1) FINAL_LIST))
  (SETQ I (+ 1 I))

)
FINAL_LIST
)






(defun roundm ( n m )
    (* m (fix ((if (minusp n) - +) (/ n (float m)) 0.5)))
)
