(DEFUN C:OFFSET_DISTANCE_GPS_MODIFIED ( / OFFSET_ENTITIES1 TRACK_ENTITY LINE TR_OFFSET_Y OFFSET_ENTITIES1 I OFFSET_ENTITIES TEMP_ELE1 LIST2 STARTING_OFFSET)
  (PROMPT "SELECT OFFSETS")
  (SETQ OFFSET_ENTITIES1 (SSGET))
  (SETQ TRACK_ENTITY (CAR(ENTSEL "\nSELECT TRACK ALIGNMENT:")))
  ;(SETQ LINE (GETSTRING "\n ENTER TRACK TYPE (UP/DN)"))
  (SETQ STARTING_OFFSET (CAR (ENTSEL "\nSELECT STARTING OFFSET:")))
  (SETQ TR_OFFSET_Y (NTH 2 (ASSOC 10 (ENTGET TRACK_ENTITY))))
  ;(SETQ OFFSET_ENTITIES1 (FORM_SSSET OFFSET_ENTITIES1))
  (SETQ I 0)
  (SETQ OFFSET_ENTITIES NIL)
  ;(WHILE (< I (LENGTH OFFSET_ENTITIES1))
    ;(SETQ TEMP_ELE1 (CDR (ASSOC 10 (ENTGET (NTH I OFFSET_ENTITIES1)))))
    ;(SETQ OFFSET_ENTITIES (CONS (LIST (NTH I OFFSET_ENTITIES1) TEMP_ELE1) OFFSET_ENTITIES))
    ;(SETQ I (+ I 1))
  ;)
  ;(SETQ OFFSET_ENTITIES (REVERSE OFFSET_ENTITIES))
  
  (SETQ OFFSET_ENTITIES (GET_OFFSET_INTERSECTION_POINTS OFFSET_ENTITIES1 TRACK_ENTITY))
  (SETQ OFFSET_ENTITIES (SORT_ENTITIES_ALONG_CURVE TRACK_ENTITY OFFSET_ENTITIES (ASSOC STARTING_OFFSET OFFSET_ENTITIES) 1 1))
  
  ;(SETQ OFFSET_ENTITIES (REVERSE (SORT_FUN OFFSET_ENTITIES 1 0)))
  
  (SETQ I 0)
  (SETQ TEMP_ELE1 NIL)
  (SETQ TEMP_ELE2 NIL)
  (SETQ TEMP_ELE3 NIL)
  (SETQ TEMP_SPAN NIL)
  (SETQ LIST2 NIL)
  (WHILE (< I (LENGTH OFFSET_ENTITIES))
  
  (IF (/= (+ I 1) (LENGTH OFFSET_ENTITIES))
 
  (PROGN
     
    ;(SETQ TEMP_ELE1 (NTH 0 (ACET-GEOM-INTERSECTWITH TRACK_ENTITY (NTH 0 (NTH I OFFSET_ENTITIES)) 0.1)))
	(SETQ TEMP_ELE1 (VLAX-SAFEARRAY->LIST (VLAX-VARIANT-VALUE (VLA-INTERSECTWITH (VLAX-ENAME->VLA-OBJECT TRACK_ENTITY) (VLAX-ENAME->VLA-OBJECT (NTH 0 (NTH I OFFSET_ENTITIES))) ACEXTENDNONE))))
	(SETQ TEMP_ELE5 (LIST (NTH 0 TEMP_ELE1) (NTH 1 TEMP_ELE1) (NTH 2 TEMP_ELE1)))
    (IF (/= (VLAX-CURVE-GETDISTATPOINT TRACK_ENTITY TEMP_ELE5)  NIL)
     (SETQ TEMP_ELE1 TEMP_ELE5)
     (SETQ TEMP_ELE1 (LIST (NTH 3 TEMP_ELE1) (NTH 4 TEMP_ELE1) (NTH 5 TEMP_ELE1)))
    )
	
	
    ;(SETQ TEMP_ELE2 (NTH 0 (ACET-GEOM-INTERSECTWITH TRACK_ENTITY (NTH 0 (NTH (+ I 1) OFFSET_ENTITIES)) 0.1)))
	(SETQ TEMP_ELE2 (VLAX-SAFEARRAY->LIST (VLAX-VARIANT-VALUE (VLA-INTERSECTWITH (VLAX-ENAME->VLA-OBJECT TRACK_ENTITY) (VLAX-ENAME->VLA-OBJECT (NTH 0 (NTH (+ I 1) OFFSET_ENTITIES))) ACEXTENDNONE))))
	(SETQ TEMP_ELE5 (LIST (NTH 0 TEMP_ELE2) (NTH 1 TEMP_ELE2) (NTH 2 TEMP_ELE2)))
    (IF (/= (VLAX-CURVE-GETDISTATPOINT TRACK_ENTITY TEMP_ELE5)  NIL)
     (SETQ TEMP_ELE2 TEMP_ELE5)
     (SETQ TEMP_ELE2 (LIST (NTH 3 TEMP_ELE2) (NTH 4 TEMP_ELE2) (NTH 5 TEMP_ELE2)))
    )
	
	
    (SETQ TEMP_SPAN (RTOS (APPROXIMATE_SPAN (DISTANCE_ON_CURVE_GPS TRACK_ENTITY TEMP_ELE2 TEMP_ELE1) 0.5) 2 2))
    (SETQ TEMP_ELE3 (VLAX-CURVE-GETPOINTATDIST TRACK_ENTITY (+ (VLAX-CURVE-GETDISTATPOINT TRACK_ENTITY TEMP_ELE1) (/ (APPROXIMATE_SPAN (DISTANCE_ON_CURVE_GPS TRACK_ENTITY TEMP_ELE2 TEMP_ELE1) 0.5) 2))))
    ;(IF (= LINE "DN")
    ;(SETQ INSERTION_POINT (POLAR TEMP_ELE3 (+ (* 1 (/ PI 2)) (ANGLE TEMP_ELE1 TEMP_ELE2)) 12.00))
    ;(SETQ INSERTION_POINT (POLAR TEMP_ELE3 (+ (* 3 (/ PI 2)) (ANGLE TEMP_ELE1 TEMP_ELE2)) 18.00))
    ;)
	
	(SETQ INSERTION_POINT TEMP_ELE3)
    (ENTMAKE (LIST
	   (CONS 0 "TEXT")
	   (CONS 1 TEMP_SPAN)
	   (LIST 10 (NTH 0 INSERTION_POINT) (NTH 1 INSERTION_POINT) 0.0)
	   (CONS 40 4.00)
	   (CONS 7 "SED_MAIN")
	   (CONS 8 "OHE-TXT-DFCC IR TC")
	   (CONS 50 (ANGLE TEMP_ELE1 TEMP_ELE2))
	 ))
  )
 )
  (SETQ I (+ I 1))
  )
)
