(DEFUN GET_CO-ORDINATES_GPS ( ENT_LIST  /  I TEMP_CHAINAGE TEMP_EFFNAME TEMP_SPAN FINAL_LIST TEMP_DFCC_CHAINAGE)

  (SETQ I 0 TEMP_CHAINAGE NIL TEMP_EFFNAME NIL TEMP_SPAN NIL FINAL_LIST NIL)
  (WHILE (< I (LENGTH ENT_LIST))
    (SETQ TEMP_NUMBER (NTH 0 (SINGLE_ELE_LIST (EXTRACT_ATTRIBUTES (NTH I ENT_LIST) (LIST "MAST_NUMBER1" ) 1) 1)))
    (SETQ TEMP_CHAINAGE (NTH 0 (SINGLE_ELE_LIST (EXTRACT_ATTRIBUTES (NTH I ENT_LIST) (LIST "CHAINAGE1" ) 1) 1)))
    (SETQ TEMP_MAST (NTH 0 (SINGLE_ELE_LIST (EXTRACT_ATTRIBUTES (NTH I ENT_LIST) (LIST "MAST_TYPE1" ) 1) 1)))
    (SETQ TEMP_IMP (NTH 0 (SINGLE_ELE_LIST (EXTRACT_ATTRIBUTES (NTH I ENT_LIST) (LIST "IMPLANTATION1" ) 1) 1)))
    (SETQ TEMP_EFFNAME (VLAX-GET-PROPERTY (VLAX-ENAME->VLA-OBJECT (NTH I ENT_LIST)) 'EFFECTIVENAME))
    (SETQ TEMP_SPAN (NTH 0 (SINGLE_ELE_LIST (EXTRACT_ATTRIBUTES (NTH I ENT_LIST) (LIST "SPAN1" ) 1) 1)))
    (SETQ TEMP_DFCC_CHAINAGE (NTH 0 (SINGLE_ELE_LIST (EXTRACT_ATTRIBUTES (NTH I ENT_LIST) (LIST "CHAINAGE2" ) 1) 1)))
	
	
	(SETQ TEMP_DFCC_KM_CHAINAGE (SUBSTR TEMP_DFCC_CHAINAGE 1 (VL-STRING-SEARCH "/" TEMP_DFCC_CHAINAGE)))
	(SETQ TEMP_DFCC_ACTUAL_CHAINAGE (SUBSTR TEMP_DFCC_CHAINAGE (+ 2 (VL-STRING-SEARCH "/" TEMP_DFCC_CHAINAGE) )))
	(SETQ TEMP_DFCC_M_CHAINAGE (SUBSTR TEMP_DFCC_ACTUAL_CHAINAGE 1 (VL-STRING-SEARCH "." TEMP_DFCC_ACTUAL_CHAINAGE)))
	
	(IF (/= (VL-STRING-SEARCH "." TEMP_DFCC_ACTUAL_CHAINAGE) NIL)
	 (SETQ TEMP_DFCC_CM_CHAINAGE (SUBSTR TEMP_DFCC_ACTUAL_CHAINAGE (+ 2 (VL-STRING-SEARCH "." TEMP_DFCC_ACTUAL_CHAINAGE))))
	  (SETQ TEMP_DFCC_CM_CHAINAGE "0.00")
	 )
	
    (SETQ TEMP_FOUNDATION_TYPE (NTH 0 (SINGLE_ELE_LIST (EXTRACT_ATTRIBUTES (NTH I ENT_LIST) (LIST "FOUNDATION_TYPE1" ) 1) 1)))
    
   (IF (/= (VL-STRING-SEARCH "-" TEMP_FOUNDATION_TYPE) NIL)
     (SETQ TEMP_FOUNDATION_WIDTH (SUBSTR TEMP_FOUNDATION_TYPE (+ 2 (VL-STRING-SEARCH "-" TEMP_FOUNDATION_TYPE))))
     (SETQ TEMP_FOUNDATION_WIDTH " ")
   )
	
	
	
    (SETQ TEMP_RD (NTH 0 (SINGLE_ELE_LIST (EXTRACT_ATTRIBUTES (NTH I ENT_LIST) (LIST "RD1" ) 1) 1)))
    (SETQ TEMP_RADIUS/SE (NTH 0 (SINGLE_ELE_LIST (EXTRACT_ATTRIBUTES (NTH I ENT_LIST) (LIST "RADIUS/SUPER_ELEVATION" ) 1) 1)))
    (SETQ TEMP_STEP_DISTANCE/EMBEDDED_LENGTH (NTH 0 (SINGLE_ELE_LIST (EXTRACT_ATTRIBUTES (NTH I ENT_LIST) (LIST "STEP_DISTANCE/EMBEDDED_LENGTH" ) 1) 1)))
    (SETQ TEMP_SUPER_BLOCK/EXTRA_DEPTH (NTH 0 (SINGLE_ELE_LIST (EXTRACT_ATTRIBUTES (NTH I ENT_LIST) (LIST "SUPER_BLOCK/EXTRA_DEPTH" ) 1) 1)))
    (SETQ TEMP_HRL (NTH 0 (SINGLE_ELE_LIST (EXTRACT_ATTRIBUTES (NTH I ENT_LIST) (LIST "DUMMY_VARIABLE2" ) 1) 1)))
	(SETQ TEMP_ANCHOR_DETAILS (NTH 0 (SINGLE_ELE_LIST (EXTRACT_ATTRIBUTES (NTH I ENT_LIST) (LIST "ANCHOR_BLOCK/ANCHOR_STEP/ANCHOR_SETTING_DISTANCE" ) 1) 1)))
    (SETQ
      FLIP (NTH 1 (NTH 0 (GET_DYNAMIC_PROPERTIES (NTH I ENT_LIST) '("STF1")))))
    
    (SETQ ROTATION (VLAX-GET-PROPERTY (VLAX-ENAME->VLA-OBJECT (NTH I ENT_LIST)) 'ROTATION))
    (SETQ TEMP_CO-ORDINATES (CDR (ASSOC 10 (ENTGET (NTH I ENT_LIST)))))
    (IF (= FLIP 0)
     (SETQ TEMP_CO-ORDINATES (MAPCAR 'RTOS (POLAR TEMP_CO-ORDINATES (+ (* 1 (/ PI 2)) ROTATION) (+ (- (ATOF TEMP_IMP) 3.00) 0.2))) TEMP_LINE "Main Down")
     (SETQ TEMP_CO-ORDINATES (MAPCAR 'RTOS (POLAR TEMP_CO-ORDINATES (+ (* 3 (/ PI 2)) ROTATION) (+ (- (ATOF TEMP_IMP) 3.00) 0.2))) TEMP_LINE "Main Up")
    )
    (SETQ FINAL_LIST (CONS (APPEND (LIST TEMP_DFCC_KM_CHAINAGE TEMP_DFCC_M_CHAINAGE TEMP_DFCC_CM_CHAINAGE TEMP_LINE TEMP_NUMBER TEMP_CHAINAGE TEMP_MAST TEMP_FOUNDATION_TYPE TEMP_RD TEMP_IMP TEMP_SPAN  TEMP_RADIUS/SE TEMP_STEP_DISTANCE/EMBEDDED_LENGTH TEMP_SUPER_BLOCK/EXTRA_DEPTH TEMP_HRL  TEMP_FOUNDATION_WIDTH) TEMP_CO-ORDINATES (LIST TEMP_ANCHOR_DETAILS)) FINAL_LIST))
    (SETQ I (+ I 1))
  )
  (REVERSE FINAL_LIST)
  
)



(DEFUN C:PRINT_LOCATION_DETAILS_NEW_EMP4 ( / )
  (SETQ WPT1 (GETPOINT "\n ENTER 1ST POINT OF POLYGON"))
  (SETQ WPT2 (GETPOINT "\n ENTER 2ND POINT OF POLYGON"))
  (SETQ WPT3 (GETPOINT "\n ENTER 3RD POINT OF POLYGON"))
  (SETQ WPT4 (GETPOINT "\n ENTER 4TH POINT OF POLYGON"))
  (SETQ BLOCKS_LIST (FORM_SSSET (SSGET "WP" (LIST WPT1 WPT2 WPT3 WPT4) (LIST (CONS 0 "INSERT")))))

  ;(SETQ STARTING_CELL (GETSTRING "\nEnter starting cell"))
  
  ;(SETQ BLOCKS_LIST (FORM_SSSET (SSGET "X" (LIST (CONS 0 "INSERT")))))
  (SETQ TRACK_ENTITY_UPTRACK (CAR(ENTSEL "\nSELECT TRACK ALIGNMENT FOR UP TRACK (DN LINE):")))
  (SETQ TRACK_ENTITY_DNTRACK (CAR(ENTSEL "\nSELECT TRACK ALIGNMENT FOR DN TRACK (UP LINE):")))
  (SETQ STARTING_POINT (GETPOINT "\nENTER STARTING POINT FOR UP TRACK (DN LINE):"))
  (SETQ STARTING_POINT_DN (GETPOINT "\nENTER STARTING POINT FOR DN TRACK (UP LINE):"))
  (SETQ BLOCK_NAME_LIST (EXTRACT_ENTITY_INFO2 BLOCKS_LIST))
  (SETQ ACC_LIST (FILTER_LIST (LIST "ACC") BLOCK_NAME_LIST 1))
  (SETQ OLC_LIST (FILTER_LIST (LIST "OLC") BLOCK_NAME_LIST 1))
  (SETQ TL_LIST (FILTER_LIST (LIST "TENSION_LENGTH") BLOCK_NAME_LIST 1))
  (SETQ ACC_LIST (BUILD_LIST (ENTITY_DFX (SINGLE_ELE_LIST ACC_LIST 0) 10 -1) (LIST 0 1)))
  (SETQ OLC_LIST (BUILD_LIST (ENTITY_DFX (SINGLE_ELE_LIST OLC_LIST 0) 10 -1) (LIST 0 1)))
  (SETQ TL_LIST  (BUILD_LIST (ENTITY_DFX (SINGLE_ELE_LIST TL_LIST 0)  10 -1) (LIST 0 1)))
  ;(COMMAND "BURST" (ENTLAST))
  (SETQ MAST_TTC (YARD_DATA_COLLECT_GPS BLOCKS_LIST '("SINGLE_CANT_MAST" "DOUBLE_CANT_MAST" "TRIPLE_CANT_MAST" "TTC" "SS0" "SS1" "SS2" "SS3" "SS4") 1 3))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  ;(SETQ ANCHOR_LIST (YARD_DATA_COLLECT WPT1 WPT2 '("ANCHOR") 1 3))
 (SETQ ANCHOR_ENTITIES (YARD_DATA_COLLECT_GPS BLOCKS_LIST '("ANCHOR") 1 5))
 (SETQ BTB_ANCHOR_ENTITIES (YARD_DATA_COLLECT_GPS BLOCKS_LIST '("BTB_ANC") 1 3))
 (SETQ ANCHOR_START (FILTER_LIST '("START") ANCHOR_ENTITIES 1))
 (SETQ ANCHOR_END (FILTER_LIST '("END") ANCHOR_ENTITIES 1))
 (SETQ MULTIPLE_CANT_MASTS (SINGLE_ELE_LIST (YARD_DATA_COLLECT_GPS BLOCKS_LIST '("DOUBLE_CANT_MAST" "TRIPLE_CANT_MAST" "SS2" "SS3") 1 3) 0))
 (SETQ MAST_UP (FILTER_LIST '("UP") MAST_TTC_DIR 1))
 (SETQ MAST_DN (FILTER_LIST '("DN") MAST_TTC_DIR 1))
  
 (SETQ ANCHOR_START  (BUILD_LIST (ENTITY_DFX (SINGLE_ELE_LIST ANCHOR_START 0)  10 -1) (LIST 0 1)))
 (SETQ ANCHOR_END  (BUILD_LIST (ENTITY_DFX (SINGLE_ELE_LIST ANCHOR_END 0)  10 -1) (LIST 0 1)))

  
  (IF (/= ANCHOR_START NIL) (SETQ ANCHOR_START_STRUCTURE_MAP_DATA (DATA_TO_STRUCTURE_MAP_SECTIONING ANCHOR_START MAST_TTC 1 1)) (SETQ ANCHOR_START NIL))
  (IF (/= ANCHOR_END NIL) (SETQ ANCHOR_END_STRUCTURE_MAP_DATA (DATA_TO_STRUCTURE_MAP_SECTIONING ANCHOR_END MAST_TTC 1 1)) (SETQ ANCHOR_END NIL))
  
  (IF (/= ACC_LIST NIL) (SETQ ACC_STRUCTURE_MAP_DATA (DATA_TO_STRUCTURE_MAP_SECTIONING ACC_LIST MAST_TTC 1 1)) (SETQ ACC_STRUCTURE_MAP_DATA NIL))



  
 (SETQ MAST_UP  (ADD_LISTS (BUILD_LIST (ENTITY_DFX (SINGLE_ELE_LIST MAST_UP 0)  10 -1) (LIST 0 1)) (N_ELE_LIST "UP" (LENGTH MAST_UP))))
 (SETQ MAST_DN  (ADD_LISTS (BUILD_LIST (ENTITY_DFX (SINGLE_ELE_LIST MAST_DN 0)  10 -1) (LIST 0 1)) (N_ELE_LIST "DN" (LENGTH MAST_DN))))

  (IF (/= BTB_ANCHOR_ENTITIES NIL) (SETQ BTB_ANCHOR_STRUCTURE_MAP_DATA_TOTAL (DATA_TO_STRUCTURE_MAP_SECTIONING BTB_ANCHOR_ENTITIES (APPEND MAST_UP MAST_DN) 1 1)) (SETQ BTB_ANCHOR_ENTITIES NIL))
  (SETQ BTB_ANCHOR_STRUCTURE_MAP_DATA_TOTAL (BUILD_LIST (SORT_ENTITIES_ALONG_CURVE1 TRACK_ENTITY_UPTRACK (ADD_LISTS BTB_ANCHOR_STRUCTURE_MAP_DATA_TOTAL (SINGLE_ELE_LIST (ENTITY_DFX (SINGLE_ELE_LIST BTB_ANCHOR_STRUCTURE_MAP_DATA_TOTAL 0)  10 -1) 1)) (LIST 1 STARTING_POINT) 1 1) (LIST 0 1 3)))

  
  (SETQ I 0 DATA_TO_PRINT NIL)
  ;(SETQ CURVE_DATA (GET_CURVE_DATA_RET))
  (SETQ MASTS_TO_BE_CONSIDERED (SINGLE_ELE_LIST MAST_TTC 0))
  
  (WHILE (< I (LENGTH MASTS_TO_BE_CONSIDERED))

  
    (SETQ LOC_DATA (NTH 0 (GET_CO-ORDINATES_GPS (LIST (NTH I MASTS_TO_BE_CONSIDERED)))))
    (SETQ TEST_ANCHOR NIL TEST_ACC NIL TEST_BTB NIL TEST_MULT NIL LOC_TYPE "NORMAL")
    ;(SETQ CURVE_DETAILS (CURVE_TEST ELE1_ELE2 CURVE_DATA))
    (IF (/= ANCHOR_START_STRUCTURE_MAP_DATA NIL) (SETQ TEST_ANCHOR_START (FILTER_LIST (LIST (NTH I MASTS_TO_BE_CONSIDERED)) ANCHOR_START_STRUCTURE_MAP_DATA 1)))
    (IF (/= ANCHOR_END_STRUCTURE_MAP_DATA NIL) (SETQ TEST_ANCHOR_END (FILTER_LIST (LIST (NTH I MASTS_TO_BE_CONSIDERED)) ANCHOR_END_STRUCTURE_MAP_DATA 1)))
    (IF (/= ACC_STRUCTURE_MAP_DATA NIL) (SETQ TEST_ACC (FILTER_LIST (LIST (NTH I MASTS_TO_BE_CONSIDERED)) ACC_STRUCTURE_MAP_DATA 1)))
    (IF (/= BTB_ANCHOR_STRUCTURE_MAP_DATA_TOTAL NIL) (SETQ TEST_BTB (FILTER_LIST (LIST (NTH I MASTS_TO_BE_CONSIDERED)) BTB_ANCHOR_STRUCTURE_MAP_DATA_TOTAL 1)))
    (IF (/= MULTIPLE_CANT_MASTS NIL) (IF (/= (VL-POSITION (NTH I MASTS_TO_BE_CONSIDERED) MULTIPLE_CANT_MASTS) NIL) (SETQ TEST_MULT 1)))
    
    (IF (/= TEST_ANCHOR_START NIL)
      (SETQ LOC_TYPE (STRCAT (NTH 0 (SINGLE_ELE_LIST (EXTRACT_ATTRIBUTES (NTH 0 (NTH 0 TEST_ANCHOR_START)) (LIST "ANCHOR_TYPE1" ) 1) 1)) "START"))
    )
    
    (IF (/= TEST_ANCHOR_END NIL)
      (SETQ LOC_TYPE (STRCAT (NTH 0 (SINGLE_ELE_LIST (EXTRACT_ATTRIBUTES (NTH 0 (NTH 0 TEST_ANCHOR_END)) (LIST "ANCHOR_TYPE1" ) 1) 1)) "END"))
    )
    
    (IF (/= TEST_ACC NIL)
      (SETQ LOC_TYPE "ACC")
    )
    (IF (/= TEST_BTB NIL)
      (SETQ LOC_TYPE (STRCAT (NTH 0 (SINGLE_ELE_LIST (EXTRACT_ATTRIBUTES (NTH 0 (NTH 0 TEST_BTB)) (LIST "ANCHOR_TYPE1" ) 1) 1)) "/" (NTH 0 (SINGLE_ELE_LIST (EXTRACT_ATTRIBUTES (NTH 0 (NTH 0 TEST_BTB)) (LIST "ANCHOR_TYPE2" ) 1) 1))))
    )
    (IF (/= TEST_MULT NIL)
      (SETQ LOC_TYPE "DOUBLE CANTILEVER LOCATION")
    )
    ;(IF (/= (NTH 0 CURVE_DETAILS) NIL) (SETQ IMPLANTATION "3.50"))
    (SETQ DATA_TO_PRINT (CONS (LIST (NTH 0 LOC_DATA) (NTH 1 LOC_DATA) (NTH 2 LOC_DATA) (NTH 3 LOC_DATA) (NTH 4 LOC_DATA) (NTH 5 LOC_DATA) (NTH 6 LOC_DATA) (NTH 7 LOC_DATA) (NTH 8 LOC_DATA)
				    (NTH 9 LOC_DATA) (NTH 10 LOC_DATA) (NTH 11 LOC_DATA) (NTH 12 LOC_DATA) (NTH 13 LOC_DATA) (NTH 14 LOC_DATA)(NTH 15 LOC_DATA)(NTH 16 LOC_DATA) (NTH 17 LOC_DATA) LOC_TYPE (NTH 19 LOC_DATA)) DATA_TO_PRINT))
    
    (SETQ I (+ I 1))

 )

  (SETQ DATA_TO_PRINT (REVERSE DATA_TO_PRINT))
  (PUTCELLSHEET "Sheet1" (COLUMN+N "A1" 0) (LIST "Section"))
  (PUTCELLSHEET "Sheet1" (COLUMN+N "A1" 1) (LIST "DFCC Chainage KM"))
  (PUTCELLSHEET "Sheet1" (COLUMN+N "A1" 2) (LIST "DFCC Chainage M"))
  (PUTCELLSHEET "Sheet1" (COLUMN+N "A1" 3) (LIST "DFCC Chainage CM"))
  (PUTCELLSHEET "Sheet1" (COLUMN+N "A1" 4) (LIST "Type of Line"))
  (PUTCELLSHEET "Sheet1" (COLUMN+N "A1" 5) (LIST "Mast Location Mainline"))
 (PUTCELLSHEET "Sheet1" (COLUMN+N "A1" 6) (LIST "Coordinate X(meter)"))
 (PUTCELLSHEET "Sheet1" (COLUMN+N "A1" 7) (LIST "Coordinate Y(meter)"))
 (PUTCELLSHEET "Sheet1" (COLUMN+N "A1" 8) (LIST "Coordinate Z(meter)"))
 (PUTCELLSHEET "Sheet1" (COLUMN+N "A1" 9) (LIST "Type of Foundation"))
 (PUTCELLSHEET "Sheet1" (COLUMN+N "A1" 10) (LIST "Depth of Foundation(meter)"))
 (PUTCELLSHEET "Sheet1" (COLUMN+N "A1" 11) (LIST "Implantaion(meter)"))
 (PUTCELLSHEET "Sheet1" (COLUMN+N "A1" 12) (LIST "Span"))
 (PUTCELLSHEET "Sheet1" (COLUMN+N "A1" 13) (LIST "Type of Mast/Portal"))
 (PUTCELLSHEET "Sheet1" (COLUMN+N "A1" 14) (LIST "Anchor Lopp"))
 (PUTCELLSHEET "Sheet1" (COLUMN+N "A1" 15) (LIST "Anti Creep Assembly"))
 (PUTCELLSHEET "Sheet1" (COLUMN+N "A1" 16) (LIST "Counterweight"))
 (PUTCELLSHEET "Sheet1" (COLUMN+N "A1" 17) (LIST "Structure Erection Drawing"))
 (PUTCELLSHEET "Sheet1" (COLUMN+N "A1" 18) (LIST "Type of Location"))
 (PUTCELLSHEET "Sheet1" (COLUMN+N "A1" 19) (LIST "Type of Cantilever"))
  (SETQ STARTING_CELL "A2")
  (PUTCELLSHEET "Sheet1" (COLUMN+N STARTING_CELL 1) (SINGLE_ELE_LIST DATA_TO_PRINT 0))
  (PUTCELLSHEET "Sheet1" (COLUMN+N STARTING_CELL 2) (SINGLE_ELE_LIST DATA_TO_PRINT 1))
  (PUTCELLSHEET "Sheet1" (COLUMN+N STARTING_CELL 3) (SINGLE_ELE_LIST DATA_TO_PRINT 2))
  (PUTCELLSHEET "Sheet1" (COLUMN+N STARTING_CELL 4) (SINGLE_ELE_LIST DATA_TO_PRINT 3))
  (PUTCELLSHEET "Sheet1" (COLUMN+N STARTING_CELL 5) (SINGLE_ELE_LIST DATA_TO_PRINT 4))
  (PUTCELLSHEET "Sheet1" (COLUMN+N STARTING_CELL 6) (SINGLE_ELE_LIST DATA_TO_PRINT 16))
  (PUTCELLSHEET "Sheet1" (COLUMN+N STARTING_CELL 7) (SINGLE_ELE_LIST DATA_TO_PRINT 17))
  ;(PUTCELLSHEET "Sheet1" (COLUMN+N STARTING_CELL 7) (SINGLE_ELE_LIST DATA_TO_PRINT 7));;
  (PUTCELLSHEET "Sheet1" (COLUMN+N STARTING_CELL 9) (SINGLE_ELE_LIST DATA_TO_PRINT 7))
  (PUTCELLSHEET "Sheet1" (COLUMN+N STARTING_CELL 23) (SINGLE_ELE_LIST DATA_TO_PRINT 15))
  (PUTCELLSHEET "Sheet1" (COLUMN+N STARTING_CELL 11) (SINGLE_ELE_LIST DATA_TO_PRINT 9))
  (PUTCELLSHEET "Sheet1" (COLUMN+N STARTING_CELL 12) (SINGLE_ELE_LIST DATA_TO_PRINT 10))
  (PUTCELLSHEET "Sheet1" (COLUMN+N STARTING_CELL 13) (SINGLE_ELE_LIST DATA_TO_PRINT 6))
  ;(PUTCELLSHEET "Sheet1" (COLUMN+N STARTING_CELL 13) (SINGLE_ELE_LIST DATA_TO_PRINT 13))
  ;(PUTCELLSHEET "Sheet1" (COLUMN+N STARTING_CELL 14) (SINGLE_ELE_LIST DATA_TO_PRINT 14))
  ;(PUTCELLSHEET "Sheet1" (COLUMN+N STARTING_CELL 15) (SINGLE_ELE_LIST DATA_TO_PRINT 15))
  ;(PUTCELLSHEET "Sheet1" (COLUMN+N STARTING_CELL 16) (SINGLE_ELE_LIST DATA_TO_PRINT 16))
  (PUTCELLSHEET "Sheet1" (COLUMN+N STARTING_CELL 18) (SINGLE_ELE_LIST DATA_TO_PRINT 18))
  (PUTCELLSHEET "Sheet1" (COLUMN+N STARTING_CELL 24) (SINGLE_ELE_LIST DATA_TO_PRINT 13))
  (PUTCELLSHEET "Sheet1" (COLUMN+N STARTING_CELL 25) (SINGLE_ELE_LIST DATA_TO_PRINT 19))
  ;(PUTCELLSHEET "Sheet1" (COLUMN+N STARTING_CELL 18) (SINGLE_ELE_LIST DATA_TO_PRINT 15))
  ;(PUTCELLSHEET "Sheet1" (COLUMN+N STARTING_CELL 18) (SINGLE_ELE_LIST DATA_TO_PRINT 18))
  
  
)
