;CODE AUTHOR : SUNEEL
;
;CODE REFERENCE : CHAITANYA SIR'S CODE
;
;CODE IS USED FOR PRINTING SOIL PROFILE
;
;DEPENDENCE : CODE MAY DEPEND ON MANY OTHER LISP FILES.
;
(DEFUN C:LOAD_SOIL_PROFILE ( / )
  (OPENEXCEL (FINDFILE (GETFILED "SELECT OBSTRUCTION FILE" "" "" 8)) "For Soil Profile" T)
)
(DEFUN C:PRINT_SOIL_PROFILE()	
  (SETQ POINT1 (GETPOINT "\n PICK STARTING POINT ON CURVE"))
  (SETQ POINT2 (GETPOINT "\n PICK ANY POINT ON CURVE IN REQUIRED DIRECTION "))
  (SETQ OS_MODE (GETVAR "OSMODE"))
  (SETQ 3DOS_MODE (GETVAR "3DOSMODE"))
  (SETVAR "OSMODE" 0)
  (SETVAR "3DOSMODE" 0)
  (SETQ START_CELL (GETSTRING "\N ENTER STARTING CELL"))
  (SETQ END_CELL (GETSTRING "\N ENTER ENDING CELL"))
  (SETQ BLOCKS_LIST (FORM_SSSET (SSGET "X" (LIST (CONS 0 "INSERT")))))
  (SETQ BLOCK_NAME_LIST (EXTRACT_ENTITY_INFO2 BLOCKS_LIST))
  (SETQ KM_STONE_LIST (FILTER_LIST (LIST "DFCC_KM_NEW") BLOCK_NAME_LIST 1))
  (SETQ KM_STONE_LIST (SORT_FUN (ENTITY_DFX (SINGLE_ELE_LIST KM_STONE_LIST 0) 10 -1) 1 0))

  (SETQ KM_START (CAR(ENTSEL "\nSELECT STARTING KM :")))

  (SETQ TRACK_ENTITY_UPTRACK (CAR(ENTSEL "\nSELECT TRACK ALIGNMENT FOR DNLINE:")))

  (SETQ TRACK_ENTITY_DNTRACK (CAR(ENTSEL "\nSELECT TRACK ALIGNMENT FOR UPLINE:")))

	(COMMAND "OFFSET" 30 TRACK_ENTITY_DNTRACK (polar POINT1 (+ (angle POINT1 POINT2) (* (/ pi 2) 3)) 10) "")
	(SETQ TRACK_ENTITY_CENTERLINE (ENTLAST))
	(SETQ EXTRA_LINE TRACK_ENTITY_CENTERLINE)
  (SETQ DIRECTION (FIND_DIRECTION TRACK_ENTITY_UPTRACK POINT1 POINT2))

  (SETQ KM_STONE_COORDINATES (COMBINE_LIST_ELEMENTS (GET_PROJECTION_FROM_POINT_LIST_FINAL TRACK_ENTITY_UPTRACK (BUILD_LIST KM_STONE_LIST (LIST 0 1)) 1)))

  (SETQ KM_STONE_COORDINATES (BUILD_LIST (SORT_ENTITIES_ALONG_CURVE TRACK_ENTITY_UPTRACK KM_STONE_COORDINATES (ASSOC KM_START KM_STONE_COORDINATES) 2 2) (LIST 0 2)))

  (SETQ KM_STONE_COORDINATES (GET_KM_STONE_COORDINATES KM_STONE_COORDINATES))
  ;;MY CODE
	(SETQ GROUPS (MAPCAR 'FIX (getCellsrow/column "For Soil Profile" (STRCAT (COLUMN+N START_CELL 0) ":" (COLUMN+N END_CELL 0)))))
	(SETQ CHAINAGE_LIST (getCellsrow/column "For Soil Profile" (STRCAT (COLUMN+N START_CELL 1) ":" (COLUMN+N END_CELL 1))))
	(SETQ DN_FORMATION (getCellsrow/column "For Soil Profile" (STRCAT (COLUMN+N START_CELL 2) ":" (COLUMN+N END_CELL 2))))
	(SETQ UP_FORMATION (getCellsrow/column "For Soil Profile" (STRCAT (COLUMN+N START_CELL 3) ":" (COLUMN+N END_CELL 3))))
	(SETQ FORMATION_TYPE (getCellsrow/column "For Soil Profile" (STRCAT (COLUMN+N START_CELL 6) ":" (COLUMN+N END_CELL 6))))
	(SETQ DLIST_3 (getCellsrow/column "For Soil Profile" (STRCAT (COLUMN+N START_CELL 9) ":" (COLUMN+N END_CELL 9))))
	(SETQ DLIST_325 (getCellsrow/column "For Soil Profile" (STRCAT (COLUMN+N START_CELL 10) ":" (COLUMN+N END_CELL 10))))
	(SETQ DLIST_35 (getCellsrow/column "For Soil Profile" (STRCAT (COLUMN+N START_CELL 11) ":" (COLUMN+N END_CELL 11))))
	(SETQ DLIST_FORMATION (getCellsrow/column "For Soil Profile" (STRCAT (COLUMN+N START_CELL 12) ":" (COLUMN+N END_CELL 12))))
	(SETQ DLIST_4 (getCellsrow/column "For Soil Profile" (STRCAT (COLUMN+N START_CELL 13) ":" (COLUMN+N END_CELL 13))))
	(SETQ DLIST_425 (getCellsrow/column "For Soil Profile" (STRCAT (COLUMN+N START_CELL 14) ":" (COLUMN+N END_CELL 14))))
	(SETQ ULIST_3 (getCellsrow/column "For Soil Profile" (STRCAT (COLUMN+N START_CELL 15) ":" (COLUMN+N END_CELL 15))))
	(SETQ ULIST_325 (getCellsrow/column "For Soil Profile" (STRCAT (COLUMN+N START_CELL 16) ":" (COLUMN+N END_CELL 16))))
	(SETQ ULIST_35 (getCellsrow/column "For Soil Profile" (STRCAT (COLUMN+N START_CELL 17) ":" (COLUMN+N END_CELL 17))))
	(SETQ ULIST_FORMATION (getCellsrow/column "For Soil Profile" (STRCAT (COLUMN+N START_CELL 18) ":" (COLUMN+N END_CELL 18))))
	(SETQ ULIST_4 (getCellsrow/column "For Soil Profile" (STRCAT (COLUMN+N START_CELL 19) ":" (COLUMN+N END_CELL 19))))
	(SETQ ULIST_425 (getCellsrow/column "For Soil Profile" (STRCAT (COLUMN+N START_CELL 20) ":" (COLUMN+N END_CELL 20))))
	(SETQ CURVE_ST (VL-REMOVE "StartCH"(VL-REMOVE 0.0 (vl-remove nil (getCellsrow/column "For Soil Profile" (STRCAT (COLUMN+N START_CELL 26) ":" (COLUMN+N END_CELL 26)))))))
	(SETQ CURVE_END (vl-remove "EndKM"(VL-REMOVE "Curve details" (VL-REMOVE 0.0(vl-remove nil (getCellsrow/column "For Soil Profile" (STRCAT (COLUMN+N START_CELL 27) ":" (COLUMN+N END_CELL 27))))))))
	(SETQ CURVE_TYPE (VL-REMOVE "Nature"(VL-REMOVE 0.0 (vl-remove nil (getCellsrow/column "For Soil Profile" (STRCAT (COLUMN+N START_CELL 28) ":" (COLUMN+N END_CELL 28)))))))
	;(setq LI '(1 1 1 1 2 2 2 2 3 3 3 3 4 4))
	(COMMAND "REGEN")
	(setq TOTAL_GROUPS (apply 'max GROUPS))
	(setq L (length GROUPS))
	(setq GROUP_LIST '())
	(setq I (APPLY 'MIN GROUPS))
	(while (< I (+ TOTAL_GROUPS 1))
		(setq SINGLE_GROUP (list (cons I (cons (VL-POSITION I GROUPS) (- (- L 1) (VL-POSITION I (REVERSE GROUPS)))))))
		(setq GROUP_LIST (append GROUP_LIST SINGLE_GROUP))
		(SETQ I (+ I 1))
	)
	(setq CANTT NIL)
	(SETQ CURRENT_GROUP (APPLY 'MIN GROUPS))
	(WHILE (< CURRENT_GROUP (+ 1 TOTAL_GROUPS))
		(SETQ START (CAR(CDR(ASSOC CURRENT_GROUP GROUP_LIST)))) ;STARTING ROW OF CURRENT GROUP
		(SETQ END (CDR(CDR(ASSOC CURRENT_GROUP GROUP_LIST)))) ;ENDING ROW OF CURRENT GROUP
		(SETQ GCHAINAGE (SUBSET CHAINAGE_LIST START END)) ;
		(SETQ GDN_FORMATION (SUBSET DN_FORMATION START END))
		(SETQ GUP_FORMATION (SUBSET UP_FORMATION START END))
		(SETQ GFORMATION_TYPE (SUBSET FORMATION_TYPE START END))
		(SETQ GDLIST_3 (SUBSET DLIST_3 START END))
		(SETQ GDLIST_325 (SUBSET DLIST_325 START END))
		(SETQ GDLIST_35 (SUBSET DLIST_35 START END))
		(SETQ GDLIST_FORMATION (SUBSET DLIST_FORMATION  START END))
		(SETQ GDLIST_4 (SUBSET DLIST_4 START END))
		(SETQ GDLIST_425 (SUBSET DLIST_425 START END))
		(SETQ GULIST_3 (SUBSET ULIST_3 START END))
		(SETQ GULIST_325 (SUBSET ULIST_325 START END))
		(SETQ GULIST_35 (SUBSET ULIST_35 START END))
		(SETQ GULIST_FORMATION (SUBSET ULIST_FORMATION  START END))
		(SETQ GULIST_4 (SUBSET ULIST_4 START END))
		(SETQ GULIST_425 (SUBSET ULIST_425 START END))
		(PROMPT " SUBSET-DONE ")
		;SELECTION BETWEEN BLOCKS
		(SETQ GCI 0)
		(SETQ CANTT "FLAT")
		(SETQ CL (LENGTH CURVE_ST))
		(WHILE (< GCI CL)
		
		(IF (OR (INRANGE (NTH 0 GCHAINAGE) (NTH GCI CURVE_ST) (NTH GCI CURVE_END)) (INRANGE (LAST GCHAINAGE) (NTH GCI CURVE_ST) (NTH GCI CURVE_END)))
			(PROGN
				(SETQ CANTT (NTH GCI CURVE_TYPE))
			)
		)
		(IF (= CANTT NIL)
		(PROGN
		(SETQ CANTT "FLAT")
		(PROMPT "CANTT DAGARAKI VACCHINDI")
		)
		)
		(SETQ GCI (+ GCI 1))
		)
		(SETQ OFFSET_END_DN (MODE GDN_FORMATION))
		(SETQ OFFSET_END_UP (MODE GUP_FORMATION))
		(SETQ GD_425 (MODE GDLIST_425))
		(SETQ GD_4 (MODE GDLIST_4))
		(SETQ GD_F (MODE GDLIST_FORMATION))
		(SETQ GD_35 (MODE GDLIST_35))
		(SETQ GD_325 (MODE GDLIST_325))
		(SETQ GD_3 (MODE GDLIST_3))
		(SETQ GU_425 (MODE GULIST_425))
		(SETQ GU_4 (MODE GULIST_4))
		(SETQ GU_F (MODE GULIST_FORMATION))
		(SETQ GU_35 (MODE GULIST_35))
		(SETQ GU_325 (MODE GULIST_325))
		(SETQ GU_3 (MODE GULIST_3))
		(PROMPT " MODE-DONE ")
		(IF (> OFFSET_END_DN 3.85)
			(PROGN
			(SETQ OFFSET_END4_DN "4.25")
			(SETQ SP_AT_4_DN GD_425)
			(SETQ OFFSET_CENTER_DN "3.50")
			(SETQ SP_AT_CENTER_DN GD_35)
			(SETQ OFFSET_START_DN "3.00")
			(SETQ SP_AT_START_DN GD_3)
			(SETQ SP_AT_END_DN GD_F)
			)
		)
		(IF (< OFFSET_END_DN 3.50)
			(PROGN
			(SETQ OFFSET_END4_DN "4.00")
			(SETQ SP_AT_4_DN GD_4)
			(SETQ OFFSET_CENTER_DN "3.25")
			(SETQ SP_AT_START_DN GD_325)
			(SETQ OFFSET_START_DN "3.00")
			(SETQ SP_AT_START_DN GD_3)
			(SETQ SP_AT_END_DN GD_F)
			)
		) 
		(IF (AND(< OFFSET_END_DN 3.85) (> OFFSET_END_DN 3.50))
			(PROGN
			(SETQ OFFSET_END4_DN "4.00")
			(SETQ SP_AT_4_DN GD_4)
			(SETQ OFFSET_CENTER_DN "3.50")
			(SETQ SP_AT_CENTER_DN GD_35)
			(SETQ OFFSET_START_DN "3.00")
			(SETQ SP_AT_START_DN GD_3)
			(SETQ SP_AT_END_DN GD_F)
			)
		)
		(IF (> OFFSET_END_UP 3.85)
			(PROGN
			(SETQ OFFSET_END4_UP "4.25")
			(SETQ SP_AT_4_UP GU_425)
			(SETQ OFFSET_CENTER_UP "3.50")
			(SETQ SP_AT_CENTER_UP GU_35)
			(SETQ OFFSET_START_UP "3.00")
			(SETQ SP_AT_START_UP GU_3)
			(SETQ SP_AT_END_UP GU_F)
			)
		) 
		(IF (< OFFSET_END_UP 3.50)
			(PROGN
			(SETQ OFFSET_END4_UP "4.00")
			(SETQ SP_AT_4_DN GU_4)
			(SETQ OFFSET_CENTER_UP "3.25")
			(SETQ SP_AT_START_UP GU_325)
			(SETQ OFFSET_START_UP "3.00")
			(SETQ SP_AT_START_UP GU_3)
			(SETQ SP_AT_END_UP GU_F)
			)
		) 
		(IF (AND(< OFSET_END_UP 3.85) (> OFFSET_END_UP 3.50))
			(PROGN
			(SETQ OFFSET_END4_UP "4.00")
			(SETQ SP_AT_4_UP GU_4)
			(SETQ OFFSET_CENTER_UP "3.50")
			(SETQ SP_AT_CENTER_UP GU_35)
			(SETQ OFFSET_START_UP "3.00")
			(SETQ SP_AT_START_UP GU_3)
			(SETQ SP_AT_END_UP GU_F)
			)
		)
		(PROMPT " DATA KUDA SELECT AYYINDHI ")
		(SETQ STKM (FIX (/ (NTH 0 GCHAINAGE) 1000)))
		(SETQ STCH (- (NTH 0 GCHAINAGE) (* STKM 1000)))
		(SETQ TSTCH (STRCAT (RTOS STKM 2 0) "/" (RTOS STCH 2 2)))
		(SETQ ENDKM (FIX (/ (LAST GCHAINAGE) 1000)))
		(SETQ ENDCH (- (+ (LAST GCHAINAGE) 20) (* ENDKM 1000)))
		(SETQ TENDCH (STRCAT (RTOS ENDKM 2 0) "/" (RTOS ENDCH 2 2)))
		(COND 
		((= CANTT "RH")
			(SETQ INSERTION_INFO (GET_OBSTRUCTION_CO-ORDINATES (ASSOC (ITOA STKM) KM_STONE_COORDINATES) STCH TRACK_ENTITY_UPTRACK TRACK_ENTITY_CENTERLINE DIRECTION)  )
			(COMMAND "INSERT" "SOIL_PROFILES_RH_CURVE" (NTH 0 INSERTION_INFO)  "1" (* (/ 180 PI) (NTH 1 INSERTION_INFO)))
			(MODIFY_ATTRIBUTES (ENTLAST) (LIST "FROM" "TO" "TYPE_OF_EMBANKMENT" ) (LIST TSTCH TENDCH (NTH 0 GFORMATION_TYPE)))
			(MODIFY_ATTRIBUTES (ENTLAST) (LIST "SP_AT_4_DN" "SP_AT_END_DN" "SP_AT_CENTER_DN" "SP_AT_START_DN" ) (LIST SP_AT_4_DN SP_AT_END_DN SP_AT_CENTER_DN SP_AT_START_DN))
			(MODIFY_ATTRIBUTES (ENTLAST) (LIST "SP_AT_4_UP" "SP_AT_END_UP" "SP_AT_CENTER_UP" "SP_AT_START_UP" ) (LIST SP_AT_4_UP SP_AT_END_DN SP_AT_CENTER_DN SP_AT_START_DN))
			(MODIFY_ATTRIBUTES (ENTLAST) (LIST "OFFSET_END4_UP" "OFFSET_END_UP" "OFFSET_CENTER_UP" "OFFSET_START_UP" ) (LIST OFFSET_END4_UP OFFSET_END_UP OFFSET_CENTER_UP OFFSET_START_UP))
			(MODIFY_ATTRIBUTES (ENTLAST) (LIST "OFFSET_END4_DN" "OFFSET_END_DN" "OFFSET_CENTER_DN" "OFFSET_START_DN" ) (LIST OFFSET_END4_DN OFFSET_END_DN OFFSET_CENTER_DN OFFSET_START_DN))
			(SETQ CANTT NIL)
		)
		((= CANTT "LH")

			(SETQ INSERTION_INFO (GET_OBSTRUCTION_CO-ORDINATES (ASSOC (ITOA STKM) KM_STONE_COORDINATES) STCH TRACK_ENTITY_UPTRACK TRACK_ENTITY_CENTERLINE DIRECTION)  )
			(COMMAND "INSERT" "SOIL_PROFILES_LH_CURVE" (NTH 0 INSERTION_INFO)  "1" (* (/ 180 PI) (NTH 1 INSERTION_INFO)))
			(MODIFY_ATTRIBUTES (ENTLAST) (LIST "FROM" "TO" "TYPE_OF_EMBANKMENT" ) (LIST TSTCH TENDCH (NTH 0 GFORMATION_TYPE)))
			(MODIFY_ATTRIBUTES (ENTLAST) (LIST "SP_AT_4_DN" "SP_AT_END_DN" "SP_AT_CENTER_DN" "SP_AT_START_DN" ) (LIST SP_AT_4_DN SP_AT_END_DN SP_AT_CENTER_DN SP_AT_START_DN))
			(MODIFY_ATTRIBUTES (ENTLAST) (LIST "SP_AT_4_UP" "SP_AT_END_UP" "SP_AT_CENTER_UP" "SP_AT_START_UP" ) (LIST SP_AT_4_UP SP_AT_END_DN SP_AT_CENTER_DN SP_AT_START_DN))
			(MODIFY_ATTRIBUTES (ENTLAST) (LIST "OFFSET_END4_UP" "OFFSET_END_UP" "OFFSET_CENTER_UP" "OFFSET_START_UP" ) (LIST OFFSET_END4_UP OFFSET_END_UP OFFSET_CENTER_UP OFFSET_START_UP))
			(MODIFY_ATTRIBUTES (ENTLAST) (LIST "OFFSET_END4_DN" "OFFSET_END_DN" "OFFSET_CENTER_DN" "OFFSET_START_DN" ) (LIST OFFSET_END4_DN OFFSET_END_DN OFFSET_CENTER_DN OFFSET_START_DN))
			(SETQ CANTT NIL)
		)
		((= CANTT "FLAT")
			(SETQ INSERTION_INFO (GET_OBSTRUCTION_CO-ORDINATES (ASSOC (ITOA STKM) KM_STONE_COORDINATES) STCH TRACK_ENTITY_UPTRACK TRACK_ENTITY_CENTERLINE DIRECTION)  )
			(COMMAND "INSERT" "SOIL PROFILES" (NTH 0 INSERTION_INFO)  "1" (* (/ 180 PI) (NTH 1 INSERTION_INFO)))
			(MODIFY_ATTRIBUTES (ENTLAST) (LIST "FROM" "TO" "TYPE_OF_EMBANKMENT" ) (LIST TSTCH TENDCH (NTH 0 GFORMATION_TYPE)))
			(MODIFY_ATTRIBUTES (ENTLAST) (LIST "SP_AT_4_DN" "SP_AT_END_DN" "SP_AT_CENTER_DN" "SP_AT_START_DN" ) (LIST SP_AT_4_DN SP_AT_END_DN SP_AT_CENTER_DN SP_AT_START_DN))
			(MODIFY_ATTRIBUTES (ENTLAST) (LIST "SP_AT_4_UP" "SP_AT_END_UP" "SP_AT_CENTER_UP" "SP_AT_START_UP" ) (LIST SP_AT_4_UP SP_AT_END_DN SP_AT_CENTER_DN SP_AT_START_DN))
			(MODIFY_ATTRIBUTES (ENTLAST) (LIST "OFFSET_END4_UP" "OFFSET_END_UP" "OFFSET_CENTER_UP" "OFFSET_START_UP" ) (LIST OFFSET_END4_UP OFFSET_END_UP OFFSET_CENTER_UP OFFSET_START_UP))
			(MODIFY_ATTRIBUTES (ENTLAST) (LIST "OFFSET_END4_DN" "OFFSET_END_DN" "OFFSET_CENTER_DN" "OFFSET_START_DN" ) (LIST OFFSET_END4_DN OFFSET_END_DN OFFSET_CENTER_DN OFFSET_START_DN))
			(SETQ CANTT NIL)
			(PROMPT " PRINT KUDA AYYINDHI ")
		)
		)
	(SETQ CURRENT_GROUP (+ CURRENT_GROUP 1))
	)
	(IF (= CURRENT_GROUP (+ 1 TOTAL_GROUPS))
		(ENTDEL EXTRA_LINE)
		(prompt "PRINTING SOIL PROFILE - DONE!")
	)
	(PRINC)
)
;(SETQ P (MODE '(0.89 0.89 0.89 0.89 0.89 0.88 0.90)))
(DEFUN MODE ( LIS )
	;(SETQ LIS '(0.9 0.89 0.9 0.9 0.9 0.88 0.90))
	(SETQ LE (LENGTH LIS))
	(SETQ C 0)
	(SETQ J 0)
	(SETQ MOD 0)
	(SETQ F '())
	(WHILE (> LE 0)
		(SETQ A (NTH 0 LIS))
		(WHILE (< J LE)
		(IF (= (NTH J LIS) A)	
			(PROGN
				(SETQ C (+ C 1));COUNTING SECTION	
			)
		)
		(SETQ J (+ J 1))
		)
		(SETQ F (APPEND F (LIST (CONS C A))))
		(SETQ LIS (VL-REMOVE A LIS))
		(SETQ LE (LENGTH LIS))
		(SETQ J 0)
		(SETQ C 0)
	)
	(SETQ SORTED (VL-SORT F (FUNCTION (lambda ( a b ) (> (car a) (car b))))))
	(SETQ MOD (CDR (CAR SORTED)))
)
(DEFUN SUBSET( SET START END / SUBSET )
	;(SETQ SET '(1 2 3 4 5 6 7 8))
	;(SETQ START 2)
	;(SETQ END 4)
	(SETQ I START)
	(SETQ SUBSET '())
	(WHILE (<= I END)
		(SETQ K (NTH I SET))
		(SETQ I (+ I 1))
		(SETQ SUBSET (APPEND SUBSET (LIST K)))
		
	)
)
(DEFUN GET_OBSTRUCTION_CO-ORDINATES ( KM_DATA CHAINAGE REFERENCE_POLYLINE MAIN_POLYLINE DIRECTION / MAIN_POINT ANGLE1 DERIVATIVE SLOPE)
  (SETQ START_POINT (NTH 1 KM_DATA) TEMP_DISTANCE NIL MAIN_POINT NIL ANGLE1 NIL DERIVATIVE NIL SLOPE NIL)
  (SETQ TEMP_DISTANCE (VLAX-CURVE-GETDISTATPOINT REFERENCE_POLYLINE (NTH 1 KM_DATA)))
    (IF (= DIRECTION "POSITIVE")
      (SETQ TEMP_DISTANCE (- TEMP_DISTANCE CHAINAGE))
      (SETQ TEMP_DISTANCE (+ TEMP_DISTANCE CHAINAGE))
    )
  (SETQ POINT_ON_REFERENCE_TRACK (VLAX-CURVE-GETPOINTATDIST REFERENCE_POLYLINE TEMP_DISTANCE))
  (IF (/= REFERENCE_POLYLINE MAIN_POLYLINE)
  (SETQ MAIN_POINT (VLAX-CURVE-GETCLOSESTPOINTTO MAIN_POLYLINE POINT_ON_REFERENCE_TRACK T))
  (SETQ MAIN_POINT POINT_ON_REFERENCE_TRACK)
  )
  
  (SETQ ANGLE1 (VLAX-CURVE-GETPARAMATPOINT MAIN_POLYLINE MAIN_POINT))
  (SETQ DERIVATIVE (VLAX-CURVE-GETFIRSTDERIV MAIN_POLYLINE ANGLE1))
  (SETQ SLOPE (ANGLE '(0 0 0) DERIVATIVE))
  (LIST MAIN_POINT SLOPE)
)
(DEFUN MODIFY_ATTRIBUTES (ENTNAME IDENTIFIER VALUE / TEMP_ELE ENT_OBJECT SAFEARRAY_SET I J)
  (SETQ SAFEARRAY_SET NIL)
  (SETQ ENT_OBJECT ENTNAME)
  (SETQ ENT_OBJECT (VLAX-ENAME->VLA-OBJECT ENT_OBJECT))
  (IF (= (VLAX-GET-PROPERTY ENT_OBJECT "HASATTRIBUTES") :VLAX-TRUE)
  (PROGN
  (SETQ	SAFEARRAY_SET
	 (VLAX-SAFEARRAY->LIST
	   (VLAX-VARIANT-VALUE
	     (VLAX-INVOKE-METHOD ENT_OBJECT "GETATTRIBUTES")
	   )
	 )
  )

  (SETQ I 0)
  (SETQ J 0)
  (SETQ LIST1 NIL)
  (WHILE (< I (LENGTH SAFEARRAY_SET))
    (SETQ TEMP_ELE (VLAX-GET-PROPERTY (NTH I SAFEARRAY_SET) "TAGSTRING"))
    (IF (/= (VL-POSITION TEMP_ELE IDENTIFIER) NIL) (PROGN (VLAX-PUT-PROPERTY (NTH I SAFEARRAY_SET) "TEXTSTRING" (NTH (VL-POSITION TEMP_ELE IDENTIFIER) VALUE)) ))
    (SETQ I (+ I 1))
  )  
)))
(defun INRANGE (NUMBER MIN MAX / A)
	(SETQ A (AND (> NUMBER MIN) (< NUMBER MAX)))
)
