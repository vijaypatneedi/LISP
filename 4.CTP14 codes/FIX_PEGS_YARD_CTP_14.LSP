(DEFUN C:FIX_PEGS_YARD_CTP_14 ( / POLYLINE_ENTITY COPY_ENTITY POINT1 POINT2 TEMP_POIN OS_MODE 3DOS_MODE DIRECTION TEMP_DISTANCE I TEMP_ELE DIST NEXT_POINT TEMP_ELE )
  (COMMAND "UCS" "W")
  ;(SETQ POLYLINE_ENTITY (CAR(ENTSEL "\n SELECT TRACK REFERENCE")))
  (SETQ COPY_ENTITY (CAR(ENTSEL "\n SELECT OBJECT FOR OFFSET")))
  ;(SETQ POINT1 (GETPOINT "\n PICK STARTING POINT ON CURVE"))
  (setq ent1 (vlax-ename->vla-object POLYLINE_ENTITY_FOR_DISTANCE_V))
  (SETQ POLYLINE_ENTITY POLYLINE_ENTITY_FOR_DISTANCE_V)
  (SETQ POINT2 (GETPOINT "\n PICK ANY POINT ON CURVE IN REQUIRED DIRECTION "))
  
  (SETQ POINT2 (VLAX-CURVE-GETCLOSESTPOINTTO (VLAX-ENAME->VLA-OBJECT POLYLINE_ENTITY_FOR_DISTANCE_V) POINT2 T))
  
  (SETQ POINT1 (vlax-safearray->list 
                    (vlax-variant-value 
                         (vla-IntersectWith ent1 (vlax-ename->vla-object COPY_ENTITY) acExtendNone) 
                    ) 
                ) 
   )
   (SETQ TEMP_POIN POINT1)
   (IF (> (LENGTH POINT1) 3) (SETQ POINT1 (LIST (CAR POINT1) (CADR POINT1)( CADDR POINT1))))

   (IF (/= (VLAX-CURVE-GETDISTATPOINT POLYLINE_ENTITY POINT1) NIL)
    (SETQ POINT1 POINT1)
    (SETQ POINT1 (LIST (NTH 3 TEMP_POIN) (NTH 4 TEMP_POIN) (NTH 5 TEMP_POIN))) 
    )
  
  (SETQ OS_MODE (GETVAR "OSMODE"))
  (SETQ 3DOS_MODE (GETVAR "3DOSMODE"))
  (SETVAR "OSMODE" 0)
  (SETVAR "3DOSMODE" 0)
  (SETQ DIRECTION (FIND_DIRECTION POLYLINE_ENTITY POINT1 POINT2))
  (SETQ TEMP_DISTANCE (VLAX-CURVE-GETDISTATPOINT POLYLINE_ENTITY POINT1))
  (SETQ I 0 TEMP_ELE NIL DIST 0)
  (WHILE (/= DIST NIL)
    (SETQ DIST (GETREAL "\n ENTER DISTANCE"))
    (IF (/= DIST NIL)
    (PROGN
    (IF (= DIRECTION "POSITIVE")
      (SETQ TEMP_DISTANCE (- TEMP_DISTANCE DIST))
      (SETQ TEMP_DISTANCE (+ TEMP_DISTANCE DIST))
    )
    (SETQ NEXT_POINT (VLAX-CURVE-GETPOINTATDIST POLYLINE_ENTITY TEMP_DISTANCE))
    (SETQ TEMP_ELE (COPY_ORTHOGONAL POLYLINE_ENTITY COPY_ENTITY POINT1 NEXT_POINT TEMP_DISTANCE))
	
	(SETQ INSERTION_POINT (LIST (/ (+ (CAR POINT1) (CAR NEXT_POINT)) 2) (/ (+ (CADR POINT1) (CADR NEXT_POINT)) 2) 0))
	(ENTMAKE (LIST
	   (CONS 0 "TEXT")
	   (CONS 1 (RTOS DIST 2 2))
	   (LIST 10 (NTH 0 INSERTION_POINT) (NTH 1 INSERTION_POINT) 0.0)
	   (CONS 40 4.00)
	   (CONS 7 "SED_MAIN")
	   (CONS 8 "OHE-TXT-DFCC IR TC")
	   (CONS 50 (ANGLE POINT1 NEXT_POINT))
	 ))
	 
	 
	 ;(SETQ P1 (LIST (+ (CAR POINT1) 30) (+ (CADR POINT1) 30)))
     ;(COMMAND "MTEXT" POINT1 P1 (RTOS DIST 2 1) "")	 
	 
    (SETQ COPY_ENTITY (NTH 0 TEMP_ELE) POINT1 (NTH 1 TEMP_ELE))
    )
    )
  )
  (SETVAR "OSMODE" OS_MODE)
  (SETVAR "3DOSMODE" 3DOS_MODE)
  (COMMAND "UCS" "P")
)



(DEFUN FIND_DIRECTION (POLYLINE_ENTITY POINT1 POINT2 / X )
  (SETQ X (- (VLAX-CURVE-GETDISTATPOINT POLYLINE_ENTITY POINT1) (VLAX-CURVE-GETDISTATPOINT POLYLINE_ENTITY POINT2)))
  (IF (= (+ X (ABS X)) 0) "NEGATIVE" "POSITIVE")
)



(DEFUN COPY_ORTHOGONAL (POLYLINE_ENTITY OBJECT PREVIOUS_POINT POINT DIST / ANGLE1 DERIVATIVE SLOPE OBJECT1 POINTS_LIST OBJECT_VLA)
(SETQ ANGLE1 (VLAX-CURVE-GETPARAMATPOINT POLYLINE_ENTITY POINT))
(SETQ DERIVATIVE (VLAX-CURVE-GETFIRSTDERIV POLYLINE_ENTITY ANGLE1))
(SETQ SLOPE (+ (/ PI 2) (ANGLE '(0 0 0) DERIVATIVE)))
(COMMAND "COPY" OBJECT "" PREVIOUS_POINT POINT)
(SETQ OBJECT1 (ENTLAST))
(SETQ POINTS_LIST (ADD_LISTS (BUILD_LIST (FILTER_LIST (LIST 10 11) (ENTGET OBJECT1) 0) (LIST 1 2)) (N_ELE_LIST 0.0 2)))
(SETQ OBJECT_VLA (VLAX-ENAME->VLA-OBJECT OBJECT1))
;(VLAX-INVOKE-METHOD (VLAX-ENAME->VLA-OBJECT OBJECT1) "ROTATE" (VLAX-3D-POINT (VLAX-CURVE-GETPOINTATDIST POLYLINE_ENTITY DIST)) (- (VLAX-GET-PROPERTY (VLAX-ENAME->VLA-OBJECT OBJECT1) "ANGLE") SLOPE))
(IF (/= (CDR(ASSOC 0 (ENTGET OBJECT1))) "XLINE")
  (COMMAND "ROTATE" OBJECT1 "" (VLAX-CURVE-GETPOINTATDIST POLYLINE_ENTITY DIST) "R" (NTH 0 POINTS_LIST) (NTH 1 POINTS_LIST) (/ (* SLOPE 180) PI))
  (COMMAND "ROTATE" OBJECT1 "" (VLAX-CURVE-GETPOINTATDIST POLYLINE_ENTITY DIST) "R" (VLAX-SAFEARRAY->LIST (VLAX-VARIANT-VALUE (VLAX-GET-PROPERTY OBJECT_VLA "BASEPOINT"))) (VLAX-SAFEARRAY->LIST (VLAX-VARIANT-VALUE (VLAX-GET-PROPERTY OBJECT_VLA "SECONDPOINT"))) (/ (* SLOPE 180) PI))
)
(LIST OBJECT1 POINT)
)
