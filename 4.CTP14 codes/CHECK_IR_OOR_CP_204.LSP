(defun C:CHECK_IR_OOR_CP_204( / I J TOTAL_LIST BLOCKS_LIST BLOCK_NAME_LIST MAST_TTC_DIR MAST_TTC OLC_LIST MAST_UP MAST_DN MAST_UP_CHAIN MAST_DN_CHAIN MAST_TTC_DN MAST_TTC_UP OLC_ENTITIES_UP_DN OLC_ENTITIES_DN OLC_ENTITIES_UP
  OLC_STRUCTURE_MAP_DATA_DN OLC_STRUCTURE_MAP_DATA_UP TEMP_DATA)

;(SETQ TOTAL_LIST (GET_TOTAL_LOC_LIST_GPS))
(SETQ BLOCKS_LIST (FORM_SSSET (SSGET "W" (GETPOINT "\n SELECT POINT1:") (GETPOINT "\n SELECT POINT2:") (LIST (CONS 0 "INSERT")))))

(SETQ UPTRACK (CAR (ENTSEL "\n SELECT UPTRACK:")))
(SETQ DNTRACK (CAR (ENTSEL "\n SELECT DNTRACK:")))
(SETQ BLOCK_NAME_LIST (EXTRACT_ENTITY_INFO2 BLOCKS_LIST))


(SETQ MAST_TTC_DIR (YARD_DATA_COLLECT_GPS BLOCKS_LIST '("DOUBLE_CANT_MAST") 1 5))
(SETQ MAST_TTC (YARD_DATA_COLLECT_GPS BLOCKS_LIST '("DOUBLE_CANT_MAST") 1 3))

(SETQ OLC_LIST (FILTER_LIST (LIST "OLC") BLOCK_NAME_LIST 1))
(SETQ OLC_LIST (BUILD_LIST (ENTITY_DFX (SINGLE_ELE_LIST OLC_LIST 0) 10 -1) (LIST 0 1)))

 
 ;(SETQ MAST_TTC_DIR (YARD_DATA_COLLECT_GPS BLOCKS_LIST '("DOUBLE_CANT_MAST") 1 5))
 ;(SETQ MAST_TTC (YARD_DATA_COLLECT_GPS BLOCKS_LIST '("SINGLE_CANT_MAST" "DOUBLE_CANT_MAST" "TRIPLE_CANT_MAST" "TTC" "SS0" "SS1" "SS2" "SS3" "SS4") 1 3))
 (SETQ MAST_UP (FILTER_LIST '("UP") MAST_TTC_DIR 1))
 (SETQ MAST_DN (FILTER_LIST '("DN") MAST_TTC_DIR 1))
 (SETQ MAST_UP (SINGLE_ELE_LIST MAST_UP 0))
 (SETQ MAST_DN (SINGLE_ELE_LIST MAST_DN 0))
 
 (SETQ MAST_UP_CHAIN (YARD_DATA_COLLECT_GPS_204 MAST_UP '("SINGLE_CANT_MAST" "DOUBLE_CANT_MAST" "TRIPLE_CANT_MAST" "TTC" "SS0" "SS1" "SS2" "SS3" "SS4") 1 "CHAINAGE1"))
 (SETQ MAST_DN_CHAIN (YARD_DATA_COLLECT_GPS_204 MAST_DN '("SINGLE_CANT_MAST" "DOUBLE_CANT_MAST" "TRIPLE_CANT_MAST" "TTC" "SS0" "SS1" "SS2" "SS3" "SS4") 1 "CHAINAGE1"))
 
 (SETQ MAST_UP_CHAIN (SORT_FUN (MAST_DISTANCE MAST_UP_CHAIN) 1 1))
 (SETQ MAST_DN_CHAIN (SORT_FUN (MAST_DISTANCE MAST_DN_CHAIN) 1 1))
 
 (SETQ MAST_UP (SINGLE_ELE_LIST MAST_UP_CHAIN 0))
 (SETQ MAST_DN (SINGLE_ELE_LIST MAST_DN_CHAIN 0))
 
 (SETQ MAST_TTC_DN (YARD_DATA_COLLECT_GPS MAST_DN '("DOUBLE_CANT_MAST") 1 3))
 (SETQ MAST_TTC_UP (YARD_DATA_COLLECT_GPS MAST_UP '("DOUBLE_CANT_MAST") 1 3))
 
 (SETQ OLC_ENTITIES_UP_DN (ANCHOR_UP_DN OLC_LIST UPTRACK DNTRACK))
 (SETQ OLC_ENTITIES_DN (FILTER_LIST (LIST "DN") OLC_ENTITIES_UP_DN 1))
 (SETQ OLC_ENTITIES_UP (FILTER_LIST (LIST "UP") OLC_ENTITIES_UP_DN 1))
 
 (SETQ OLC_ENTITIES_DN (BUILD_LIST (ENTITY_DFX (SINGLE_ELE_LIST OLC_ENTITIES_DN 0)  10 -1) (LIST 0 1)))
 (SETQ OLC_ENTITIES_UP (BUILD_LIST (ENTITY_DFX (SINGLE_ELE_LIST OLC_ENTITIES_UP 0)  10 -1) (LIST 0 1)))
 
 
 
 
 (IF (/= OLC_ENTITIES_DN NIL) (SETQ OLC_STRUCTURE_MAP_DATA_DN (REVERSE (DATA_TO_STRUCTURE_MAP_SECTIONING OLC_ENTITIES_DN MAST_TTC_DN 1 1))) (SETQ OLC_STRUCTURE_MAP_DATA_DN NIL))
 (IF (/= OLC_ENTITIES_UP NIL) (SETQ OLC_STRUCTURE_MAP_DATA_UP (REVERSE (DATA_TO_STRUCTURE_MAP_SECTIONING OLC_ENTITIES_UP MAST_TTC_UP 1 1))) (SETQ OLC_STRUCTURE_MAP_DATA_UP NIL))

 (SETQ I 0)
 (WHILE (< I (LENGTH OLC_STRUCTURE_MAP_DATA_DN))
 (SETQ TEMP_DATA (NTH 1 (NTH I OLC_STRUCTURE_MAP_DATA_DN)))
 (SETQ J 0)
  (WHILE (< J (LENGTH MAST_DN))
   (IF (EQUAL TEMP_DATA (NTH J MAST_DN))
    (PROGN
     (CHECK_OOR_IR (NTH (- J 1) MAST_DN))
	 (CHECK_IR_IR (NTH J MAST_DN))
	 (CHECK_IR_OOR (NTH  (+ J 1) MAST_DN))
    )
   )

  (SETQ J (+ J 1))
  )
 
 (SETQ I (+ I 1))
 )
 
 
 (SETQ I 0)
 (WHILE (< I (LENGTH OLC_STRUCTURE_MAP_DATA_UP))
 (SETQ TEMP_DATA (NTH 1 (NTH I OLC_STRUCTURE_MAP_DATA_UP)))
 (SETQ J 0)
  (WHILE (< J (LENGTH MAST_UP))
   (IF (EQUAL TEMP_DATA (NTH J MAST_UP))
    (PROGN
     (CHECK_OOR_IR (NTH (- J 1) MAST_UP))
	 (CHECK_IR_IR (NTH J MAST_UP))
	 (CHECK_IR_OOR (NTH  (+ J 1) MAST_UP))
    )
   )

  (SETQ J (+ J 1))
  )
 
 (SETQ I (+ I 1))
 )
 
 
 

)


(defun C:CORRECT_IR_OOR_CP_204( / I J TOTAL_LIST BLOCKS_LIST BLOCK_NAME_LIST MAST_TTC_DIR MAST_TTC OLC_LIST MAST_UP MAST_DN MAST_UP_CHAIN MAST_DN_CHAIN MAST_TTC_DN MAST_TTC_UP OLC_ENTITIES_UP_DN OLC_ENTITIES_DN OLC_ENTITIES_UP
  OLC_STRUCTURE_MAP_DATA_DN OLC_STRUCTURE_MAP_DATA_UP TEMP_DATA)

;(SETQ TOTAL_LIST (GET_TOTAL_LOC_LIST_GPS))
(SETQ BLOCKS_LIST (FORM_SSSET (SSGET "W" (GETPOINT "\n SELECT POINT1:") (GETPOINT "\n SELECT POINT2:") (LIST (CONS 0 "INSERT")))))

(SETQ UPTRACK (CAR (ENTSEL "\n SELECT UPTRACK:")))
(SETQ DNTRACK (CAR (ENTSEL "\n SELECT DNTRACK:")))
(SETQ BLOCK_NAME_LIST (EXTRACT_ENTITY_INFO2 BLOCKS_LIST))


(SETQ MAST_TTC_DIR (YARD_DATA_COLLECT_GPS BLOCKS_LIST '("DOUBLE_CANT_MAST") 1 5))
(SETQ MAST_TTC (YARD_DATA_COLLECT_GPS BLOCKS_LIST '("DOUBLE_CANT_MAST") 1 3))

(SETQ OLC_LIST (FILTER_LIST (LIST "OLC") BLOCK_NAME_LIST 1))
(SETQ OLC_LIST (BUILD_LIST (ENTITY_DFX (SINGLE_ELE_LIST OLC_LIST 0) 10 -1) (LIST 0 1)))

 
 ;(SETQ MAST_TTC_DIR (YARD_DATA_COLLECT_GPS BLOCKS_LIST '("DOUBLE_CANT_MAST") 1 5))
 ;(SETQ MAST_TTC (YARD_DATA_COLLECT_GPS BLOCKS_LIST '("SINGLE_CANT_MAST" "DOUBLE_CANT_MAST" "TRIPLE_CANT_MAST" "TTC" "SS0" "SS1" "SS2" "SS3" "SS4") 1 3))
 (SETQ MAST_UP (FILTER_LIST '("UP") MAST_TTC_DIR 1))
 (SETQ MAST_DN (FILTER_LIST '("DN") MAST_TTC_DIR 1))
 (SETQ MAST_UP (SINGLE_ELE_LIST MAST_UP 0))
 (SETQ MAST_DN (SINGLE_ELE_LIST MAST_DN 0))
 
 (SETQ MAST_UP_CHAIN (YARD_DATA_COLLECT_GPS_204 MAST_UP '("SINGLE_CANT_MAST" "DOUBLE_CANT_MAST" "TRIPLE_CANT_MAST" "TTC" "SS0" "SS1" "SS2" "SS3" "SS4") 1 "CHAINAGE1"))
 (SETQ MAST_DN_CHAIN (YARD_DATA_COLLECT_GPS_204 MAST_DN '("SINGLE_CANT_MAST" "DOUBLE_CANT_MAST" "TRIPLE_CANT_MAST" "TTC" "SS0" "SS1" "SS2" "SS3" "SS4") 1 "CHAINAGE1"))
 
 (SETQ MAST_UP_CHAIN (SORT_FUN (MAST_DISTANCE MAST_UP_CHAIN) 1 1))
 (SETQ MAST_DN_CHAIN (SORT_FUN (MAST_DISTANCE MAST_DN_CHAIN) 1 1))
 
 (SETQ MAST_UP (SINGLE_ELE_LIST MAST_UP_CHAIN 0))
 (SETQ MAST_DN (SINGLE_ELE_LIST MAST_DN_CHAIN 0))
 
 (SETQ MAST_TTC_DN (YARD_DATA_COLLECT_GPS MAST_DN '("DOUBLE_CANT_MAST") 1 3))
 (SETQ MAST_TTC_UP (YARD_DATA_COLLECT_GPS MAST_UP '("DOUBLE_CANT_MAST") 1 3))
 
 (SETQ OLC_ENTITIES_UP_DN (ANCHOR_UP_DN OLC_LIST UPTRACK DNTRACK))
 (SETQ OLC_ENTITIES_DN (FILTER_LIST (LIST "DN") OLC_ENTITIES_UP_DN 1))
 (SETQ OLC_ENTITIES_UP (FILTER_LIST (LIST "UP") OLC_ENTITIES_UP_DN 1))
 
 (SETQ OLC_ENTITIES_DN (BUILD_LIST (ENTITY_DFX (SINGLE_ELE_LIST OLC_ENTITIES_DN 0)  10 -1) (LIST 0 1)))
 (SETQ OLC_ENTITIES_UP (BUILD_LIST (ENTITY_DFX (SINGLE_ELE_LIST OLC_ENTITIES_UP 0)  10 -1) (LIST 0 1)))
 
 
 
 
 (IF (/= OLC_ENTITIES_DN NIL) (SETQ OLC_STRUCTURE_MAP_DATA_DN (REVERSE (DATA_TO_STRUCTURE_MAP_SECTIONING OLC_ENTITIES_DN MAST_TTC_DN 1 1))) (SETQ OLC_STRUCTURE_MAP_DATA_DN NIL))
 (IF (/= OLC_ENTITIES_UP NIL) (SETQ OLC_STRUCTURE_MAP_DATA_UP (REVERSE (DATA_TO_STRUCTURE_MAP_SECTIONING OLC_ENTITIES_UP MAST_TTC_UP 1 1))) (SETQ OLC_STRUCTURE_MAP_DATA_UP NIL))

 (SETQ I 0)
 (WHILE (< I (LENGTH OLC_STRUCTURE_MAP_DATA_DN))
 (SETQ TEMP_DATA (NTH 1 (NTH I OLC_STRUCTURE_MAP_DATA_DN)))
 (SETQ J 0)
  (WHILE (< J (LENGTH MAST_DN))
   (IF (EQUAL TEMP_DATA (NTH J MAST_DN))
    (PROGN
     (CORRECT_OOR_IR (NTH (- J 1) MAST_DN))
	 (CORRECT_IR_IR (NTH J MAST_DN))
	 (CORRECT_IR_OOR (NTH  (+ J 1) MAST_DN))
    )
   )

  (SETQ J (+ J 1))
  )
 
 (SETQ I (+ I 1))
 )
 
 
 (SETQ I 0)
 (WHILE (< I (LENGTH OLC_STRUCTURE_MAP_DATA_UP))
 (SETQ TEMP_DATA (NTH 1 (NTH I OLC_STRUCTURE_MAP_DATA_UP)))
 (SETQ J 0)
  (WHILE (< J (LENGTH MAST_UP))
   (IF (EQUAL TEMP_DATA (NTH J MAST_UP))
    (PROGN
     (CORRECT_OOR_IR (NTH (- J 1) MAST_UP))
	 (CORRECT_IR_IR (NTH J MAST_UP))
	 (CORRECT_IR_OOR (NTH  (+ J 1) MAST_UP))
    )
   )

  (SETQ J (+ J 1))
  )
 
 (SETQ I (+ I 1))
 )
 
 
 

)




(defun C:CHECK_ACC_CP_204( / I J TOTAL_LIST BLOCKS_LIST BLOCK_NAME_LIST MAST_TTC_DIR MAST_TTC OLC_LIST MAST_UP MAST_DN MAST_UP_CHAIN MAST_DN_CHAIN MAST_TTC_DN MAST_TTC_UP OLC_ENTITIES_UP_DN OLC_ENTITIES_DN OLC_ENTITIES_UP
  OLC_STRUCTURE_MAP_DATA_DN OLC_STRUCTURE_MAP_DATA_UP TEMP_DATA)

(SETQ BLOCKS_LIST (FORM_SSSET (SSGET "W" (GETPOINT "\n SELECT POINT1:") (GETPOINT "\n SELECT POINT2:") (LIST (CONS 0 "INSERT")))))
(SETQ MAST_TTC (YARD_DATA_COLLECT_GPS BLOCKS_LIST '("SINGLE_CANT_MAST" "DOUBLE_CANT_MAST" "TRIPLE_CANT_MAST" "TTC" "SS0" "SS1" "SS2" "SS3" "SS4") 1 3))
(SETQ UPTRACK (CAR (ENTSEL "\n SELECT UPTRACK:")))
(SETQ DNTRACK (CAR (ENTSEL "\n SELECT DNTRACK:")))
(SETQ BLOCK_NAME_LIST (EXTRACT_ENTITY_INFO2 BLOCKS_LIST))
(SETQ ACC_LIST (FILTER_LIST (LIST "ACC") BLOCK_NAME_LIST 1)) 
(SETQ ACC_LIST (BUILD_LIST (ENTITY_DFX (SINGLE_ELE_LIST ACC_LIST 0) 10 -1) (LIST 0 1)))
(IF (/= ACC_LIST NIL) (SETQ ACC_STRUCTURE_MAP_DATA (DATA_TO_STRUCTURE_MAP_SECTIONING ACC_LIST MAST_TTC 1 1)) (SETQ ACC_STRUCTURE_MAP_DATA NIL))
(SETQ I 0)
 (WHILE (< I (LENGTH ACC_STRUCTURE_MAP_DATA))
  (SETQ ACC_STATUS (NTH 1 (NTH 0 (FILTER_LIST (LIST "ACC") (GET_ATTRIBUTES (NTH 1 (NTH I ACC_STRUCTURE_MAP_DATA))) 0))))
   (IF (/= ACC_STATUS "1")
    (CHANGE_COLOR (NTH 1 (NTH I ACC_STRUCTURE_MAP_DATA)))
   )
 
   (SETQ I (+ I 1))
  ) 
  
 )

(DEFUN CHECK_IR_OOR(ENT_DOUBLE / WIRE_SYS1 WIRE_SYS2)
 (SETQ WIRE_SYS1 (NTH 1 (NTH 0 (FILTER_LIST (LIST "WIRE_NATURE1") (GET_ATTRIBUTES ENT_DOUBLE) 0))))
 (SETQ WIRE_SYS2 (NTH 1 (NTH 0 (FILTER_LIST (LIST "WIRE_NATURE2") (GET_ATTRIBUTES ENT_DOUBLE) 0))))

 (IF (NOT (AND (= WIRE_SYS1 "IR") (= WIRE_SYS2 "OOR")))
    (CHANGE_COLOR ENT_DOUBLE)
 )
 
)

(DEFUN CHECK_OOR_IR(ENT_DOUBLE / WIRE_SYS1 WIRE_SYS2)
 (SETQ WIRE_SYS1 (NTH 1 (NTH 0 (FILTER_LIST (LIST "WIRE_NATURE1") (GET_ATTRIBUTES ENT_DOUBLE) 0))))
 (SETQ WIRE_SYS2 (NTH 1 (NTH 0 (FILTER_LIST (LIST "WIRE_NATURE2") (GET_ATTRIBUTES ENT_DOUBLE) 0))))

 (IF (NOT (AND (= WIRE_SYS1 "OOR") (= WIRE_SYS2 "IR")))
    (CHANGE_COLOR ENT_DOUBLE)
 )
 
)

(DEFUN CHECK_IR_IR(ENT_DOUBLE / WIRE_SYS1 WIRE_SYS2)
 (SETQ WIRE_SYS1 (NTH 1 (NTH 0 (FILTER_LIST (LIST "WIRE_NATURE1") (GET_ATTRIBUTES ENT_DOUBLE) 0))))
 (SETQ WIRE_SYS2 (NTH 1 (NTH 0 (FILTER_LIST (LIST "WIRE_NATURE2") (GET_ATTRIBUTES ENT_DOUBLE) 0))))

 (IF (NOT (AND (= WIRE_SYS1 "IR") (= WIRE_SYS2 "IR")))
    (CHANGE_COLOR ENT_DOUBLE)
 )
 
)


(DEFUN CORRECT_IR_OOR(ENT_DOUBLE / WIRE_SYS1 WIRE_SYS2)
 (SETQ WIRE_SYS1 (NTH 1 (NTH 0 (FILTER_LIST (LIST "WIRE_NATURE1") (GET_ATTRIBUTES ENT_DOUBLE) 0))))
 (SETQ WIRE_SYS2 (NTH 1 (NTH 0 (FILTER_LIST (LIST "WIRE_NATURE2") (GET_ATTRIBUTES ENT_DOUBLE) 0))))

 (IF (NOT (AND (= WIRE_SYS1 "IR") (= WIRE_SYS2 "OOR")))
    (PROGN 
	(CHANGE_COLOR ENT_DOUBLE)
	(MODIFY_ATTRIBUTES ENT_DOUBLE (LIST "WIRE_NATURE1" "WIRE_NATURE2") (LIST "IR" "OOR"))
	)
 )
 
)

(DEFUN CORRECT_OOR_IR(ENT_DOUBLE / WIRE_SYS1 WIRE_SYS2)
 (SETQ WIRE_SYS1 (NTH 1 (NTH 0 (FILTER_LIST (LIST "WIRE_NATURE1") (GET_ATTRIBUTES ENT_DOUBLE) 0))))
 (SETQ WIRE_SYS2 (NTH 1 (NTH 0 (FILTER_LIST (LIST "WIRE_NATURE2") (GET_ATTRIBUTES ENT_DOUBLE) 0))))

 (IF (NOT (AND (= WIRE_SYS1 "OOR") (= WIRE_SYS2 "IR")))
    (PROGN 
	(CHANGE_COLOR ENT_DOUBLE)
	(MODIFY_ATTRIBUTES ENT_DOUBLE (LIST "WIRE_NATURE1" "WIRE_NATURE2") (LIST "OOR" "IR"))
	)
 )
 
)

(DEFUN CORRECT_IR_IR(ENT_DOUBLE / WIRE_SYS1 WIRE_SYS2)
 (SETQ WIRE_SYS1 (NTH 1 (NTH 0 (FILTER_LIST (LIST "WIRE_NATURE1") (GET_ATTRIBUTES ENT_DOUBLE) 0))))
 (SETQ WIRE_SYS2 (NTH 1 (NTH 0 (FILTER_LIST (LIST "WIRE_NATURE2") (GET_ATTRIBUTES ENT_DOUBLE) 0))))

 (IF (NOT (AND (= WIRE_SYS1 "IR") (= WIRE_SYS2 "IR")))
    (PROGN 
	(CHANGE_COLOR ENT_DOUBLE)
	(MODIFY_ATTRIBUTES ENT_DOUBLE (LIST "WIRE_NATURE1" "WIRE_NATURE2") (LIST "IR" "IR"))
	)
 )
 
)

(defun change_color(ent / list1 )

 (setq list1 (entget ent))
 (setq list1 (append list1 (list (cons 62 3))))
 (entmod list1)
 (entupd ent)
 )


(DEFUN ANCHOR_UP_DN (ENT_LIST UPTRACK DNTRACK / FINAL_LIST I ent1 ent2 P1 P2 PROJECTION_UPTRACK PROJECTION_DNTRACK DIST_UPTRACK DIST_DNTRACK LINE_TYPE)
   (setq ent1 (vlax-ename->vla-object UPTRACK))
    (setq ent2 (vlax-ename->vla-object DNTRACK))
	(SETQ I 0 FINAL_LIST NIL)
   (WHILE (< I (LENGTH ENT_LIST))
   (SETQ P2 (NTH 1 (NTH I ENT_LIST)))
   (SETQ PROJECTION_UPTRACK (vlax-curve-getclosestpointto ent1 P2))
   (SETQ PROJECTION_DNTRACK (vlax-curve-getclosestpointto ent2 P2))
   (SETQ DIST_UPTRACK (DISTANCE2D P2 PROJECTION_UPTRACK))
   (SETQ DIST_DNTRACK (DISTANCE2D P2 PROJECTION_DNTRACK))
   (IF (< DIST_UPTRACK DIST_DNTRACK)
      (SETQ LINE_TYPE "DN")
	  (SETQ LINE_TYPE "UP")
	  )
	  (SETQ FINAL_LIST (CONS (LIST (NTH 0 (NTH I ENT_LIST)) LINE_TYPE) FINAL_LIST))
	  (SETQ I (+ I 1))
    )
 FINAL_LIST
)



(DEFUN YARD_DATA_COLLECT_GPS_204 (ENTITY_LIST BLOCKNAME_LIST J ATTRIBUTE / LIST1 I TEMP_ELE TEMP_LIST LIST2)

  (SETQ LIST1 (SINGLE_ELE_LIST (FILTER_LIST BLOCKNAME_LIST (DATA_COLLECT_GPS ENTITY_LIST BLOCKNAME_LIST 2 -1)  0) 1))
  (SETQ I 0)
  (SETQ TEMP_ELE NIL)
  (SETQ TEMP_LIST NIL)
  (SETQ LIST2 NIL)
  (WHILE (< I (LENGTH LIST1))
    (SETQ TEMP_LIST (YARD_STRUCTURE_INFO_GPS (NTH I LIST1)))
	(SETQ A (NTH 1 (ASSOC 4 (YARD_STRUCTURE_INFO_GPS (NTH I LIST1)))))
  (SETQ TEMP_ELE (LIST (NTH 1 (ASSOC J  TEMP_LIST)) (NTH 1 (ASSOC ATTRIBUTE A))))
  (SETQ LIST2 (CONS TEMP_ELE LIST2))
    (SETQ I (+ I 1))
    )
  (REVERSE LIST2)
)



(DEFUN MAST_DISTANCE (LIST1)
	(SETQ I 0)
	(SETQ LIST2 NIL)
	(WHILE (< I (LENGTH LIST1))
	(SETQ TEMP_DFCC_CHAINAGE (NTH 1 (NTH I LIST1)))
	(SETQ TEMP_DFCC_KM_CHAINAGE (SUBSTR TEMP_DFCC_CHAINAGE 1 (VL-STRING-SEARCH "/" TEMP_DFCC_CHAINAGE)))
	(SETQ TEMP_DFCC_ACTUAL_CHAINAGE (SUBSTR TEMP_DFCC_CHAINAGE (+ 2 (VL-STRING-SEARCH "/" TEMP_DFCC_CHAINAGE) )))
	(SETQ DISTANCE1 (+ (* (ATOF TEMP_DFCC_KM_CHAINAGE) 1000.00) (ATOF TEMP_DFCC_ACTUAL_CHAINAGE)))
	
	(SETQ LIST2 (CONS (LIST (NTH 0 (NTH I LIST1)) DISTANCE1) LIST2))
	(SETQ I (+ I 1))
	)
	
	LIST2
	)
	
	
(DEFUN FILTER_LIST_CP_204 (LIST1 LIST2 POSITION / I LOOP_ELE TEMP_ELE LIST3)
  (SETQ I 0)
  (SETQ LIST3 NIL)
  (WHILE (< I (LENGTH LIST2))
    (IF (/= (NTH I LIST2) NIL)
	(PROGN
	(SETQ LOOP_ELE (NTH POSITION (NTH I LIST2)))
    (IF	(>= (VL-POSITION LOOP_ELE LIST1) 0)
      (PROGN (SETQ TEMP_ELE (NTH I LIST2))
	     (SETQ LIST3 (CONS TEMP_ELE LIST3))
      )
    )
	)
	)
    (SETQ I (+ I 1))
  )
  (SETQ LIST3 (REVERSE LIST3))
)
