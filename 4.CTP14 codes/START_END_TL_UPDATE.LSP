(DEFUN C:START_END_TL_UPDATE (/ BLOCKS_LIST BLOCK_NAME_LIST TL_LIST MAST_TTC MAST_TTC_DIR TL_STRUCTURE_MAP_DATA I MAST TL TEMP_MAST TEMP_DFCC_CHAINAGE 
                                TEMP_DFCC_KM_CHAINAGE TEMP_DFCC_ACTUAL_CHAINAGE TEMP_DFCC_CHAINAGE1 TEMP_DFCC_KM_CHAINAGE1 TEMP_DFCC_ACTUAL_CHAINAGE1 TL_DIST DIST2 DIST1 TEMP_LOC
								     )
(SETQ BLOCKS_LIST (FORM_SSSET (SSGET "X" (LIST (CONS 0 "INSERT")))))
(SETQ BLOCK_NAME_LIST (EXTRACT_ENTITY_INFO2 BLOCKS_LIST))
(SETQ TL_LIST (FILTER_LIST (LIST "TENSION_LENGTH") BLOCK_NAME_LIST 1))
(SETQ TL_LIST  (BUILD_LIST (ENTITY_DFX (SINGLE_ELE_LIST TL_LIST 0)  10 -1) (LIST 0 1)))
(SETQ MAST_TTC (YARD_DATA_COLLECT_GPS BLOCKS_LIST '("SINGLE_CANT_MAST" "DOUBLE_CANT_MAST" "TRIPLE_CANT_MAST" "TTC" "SS0" "SS1" "SS2" "SS3" "SS4") 1 3))
;(SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
(IF (/= TL_LIST NIL) (SETQ TL_STRUCTURE_MAP_DATA (DATA_TO_STRUCTURE_MAP_SECTIONING TL_LIST MAST_TTC 1 1)) (SETQ TL_STRUCTURE_MAP_DATA NIL))
(SETQ I 0)
(WHILE (/= I 100)
(SETQ MAST (NTH 0 (ENTSEL "\n SELECT MAST")))
(SETQ TL (NTH 0 (ENTSEL "\n SELECT TL")))
  (SETQ TEMP_MAST (NTH 0 (SINGLE_ELE_LIST (FILTER_LIST (LIST TL) TL_STRUCTURE_MAP_DATA 0) 1)))
  
  (SETQ TEMP_DFCC_CHAINAGE (NTH 1 (ASSOC "CHAINAGE1" (GET_ATTRIBUTES1 TEMP_MAST))))
  (SETQ TEMP_DFCC_KM_CHAINAGE (ATOF (SUBSTR TEMP_DFCC_CHAINAGE 1 (VL-STRING-SEARCH "/" TEMP_DFCC_CHAINAGE))))
  (SETQ TEMP_DFCC_ACTUAL_CHAINAGE (ATOF (SUBSTR TEMP_DFCC_CHAINAGE (+ 2 (VL-STRING-SEARCH "/" TEMP_DFCC_CHAINAGE) ))))
  (SETQ DIST1 (+ (* TEMP_DFCC_KM_CHAINAGE 1000.00) TEMP_DFCC_ACTUAL_CHAINAGE))
  
  (SETQ TEMP_DFCC_CHAINAGE1 (NTH 1 (ASSOC "CHAINAGE1" (GET_ATTRIBUTES1 MAST))))
  (SETQ TEMP_DFCC_KM_CHAINAGE1 (ATOF (SUBSTR TEMP_DFCC_CHAINAGE1 1 (VL-STRING-SEARCH "/" TEMP_DFCC_CHAINAGE1))))
  (SETQ TEMP_DFCC_ACTUAL_CHAINAGE1 (ATOF (SUBSTR TEMP_DFCC_CHAINAGE1 (+ 2 (VL-STRING-SEARCH "/" TEMP_DFCC_CHAINAGE1) ))))
  (SETQ DIST2 (+ (* TEMP_DFCC_KM_CHAINAGE1 1000.00) TEMP_DFCC_ACTUAL_CHAINAGE1))
  
  (SETQ TL_DIST (RTOS (ABS (- DIST1 DIST2)) 2 2))
  (SETQ TEMP_LOC (NTH 1 (ASSOC "MAST_NUMBER1" (GET_ATTRIBUTES1 MAST))))
  
  (MODIFY_ATTRIBUTES TL (LIST "TENSION_LENGTH" "LOCATION_NUM" "CHAINAGE") 
                        (LIST TL_DIST TEMP_LOC TEMP_DFCC_CHAINAGE1))
  
  )
  )
