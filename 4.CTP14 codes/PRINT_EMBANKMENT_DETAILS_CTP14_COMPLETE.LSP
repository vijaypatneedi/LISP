(DEFUN C:PRINT_EMBANKMENT_DETAILS_CTP_14_COMPLETE ( / BLOCKS_LIST TRACK_FLAG MAST_TTC_DIR ENT_LIST DFCC_TRACK_CENTER IR_TRACK_CENTER I MAST ROTATION INSERTION_POINT PROJECTION_POINT1 PROJECTION_POINT2 PROJECTION_POINT3 PROJECTION_POINT4 FINAL_INSERTION_POINT LOC_NO  CHAINAGE IMPLANTATION TEMP_KM TEMP_CHAINAGE TEMP_LIST FINAL_LIST)
;(SETQ ENT_LIST (FORM_SSSET (SSGET)))
  ;(SETQ START_CELL (GETSTRING "\n ENTER START CELL IN THE EXCEL SHEET:"))
  (SETQ START_CELL "A1")
  (SETQ BLOCKS_LIST (FORM_SSSET (SSGET "X" (LIST (CONS 0 "INSERT")))))
  (SETQ MAST_TTC_DIR (YARD_DATA_COLLECT_GPS BLOCKS_LIST '("SINGLE_CANT_MAST" "DOUBLE_CANT_MAST" "TRIPLE_CANT_MAST" "TTC" "SS0" "SS1" "SS2" "SS3" "SS4") 1 5))
  ;(SETQ TRACK_FLAG (GETSTRING "\n FOR WHICH TRACK YOU WANT???, TYPE UP OR DN:"))
  (SETQ TRACK_FLAG "DN")
  (SETQ ENT_LIST (SINGLE_ELE_LIST (FILTER_LIST (LIST TRACK_FLAG) MAST_TTC_DIR 1) 0))
  
  (SETQ ENT_LIST_CHAIN (YARD_DATA_COLLECT_GPS_204 ENT_LIST '("SINGLE_CANT_MAST" "DOUBLE_CANT_MAST" "TRIPLE_CANT_MAST" "TTC" "SS0" "SS1" "SS2" "SS3" "SS4") 1 "CHAINAGE2"))
  (SETQ ENT_LIST_CHAIN (SORT_FUN (MAST_DISTANCE ENT_LIST_CHAIN) 1 1))
  (SETQ ENT_LIST (SINGLE_ELE_LIST ENT_LIST_CHAIN 0))

(SETQ DFCC_DN_TRACK_CENTER (CAR(ENTSEL "\n SELECT DFCC DN LINE TRACK CENTER:")))
(SETQ DFCC_UP_TRACK_CENTER (CAR(ENTSEL "\n SELECT DFCC UP LINE TRACK CENTER:")))
;(SETQ IR_TRACK_CENTER (CAR(ENTSEL "\n SELECT IR TRACK CENTER:")))
(SETQ FORMATION_DN (CAR(ENTSEL "\n SELECT DN TRACK FORMATION:")))
(SETQ FORMATION_UP (CAR(ENTSEL "\n SELECT UP TRACK FORMATION:")))
(SETQ DFCC_DN_TRACK_CENTER (VLAX-ENAME->VLA-OBJECT DFCC_DN_TRACK_CENTER))
(SETQ DFCC_UP_TRACK_CENTER (VLAX-ENAME->VLA-OBJECT DFCC_UP_TRACK_CENTER))
;(SETQ IR_TRACK_CENTER (VLAX-ENAME->VLA-OBJECT IR_TRACK_CENTER))
(SETQ FORMATION_DN (VLAX-ENAME->VLA-OBJECT FORMATION_DN))
(SETQ FORMATION_UP (VLAX-ENAME->VLA-OBJECT FORMATION_UP))
(SETQ I 0 MAST NIL ROTATION NIL INSERTION_POINT NIL PROJECTION_POINT1 NIL PROJECTION_POINT2 NIL PROJECTION_POINT3 NIL PROJECTION_POINT4 NIL FINAL_INSERTION_POINT NIL LOC_NO NIL CHAINAGE NIL IMPLANTATION NIL TEMP_KM NIL TEMP_CHAINAGE NIL TEMP_LIST NIL FINAL_LIST NIL)
(WHILE (< I (LENGTH ENT_LIST))
  (SETQ MAST (VLAX-ENAME->VLA-OBJECT (NTH I ENT_LIST)))
  
  (SETQ INSERTION_POINT (VLAX-SAFEARRAY->LIST (VLAX-VARIANT-VALUE (VLAX-GET-PROPERTY MAST 'INSERTIONPOINT))))
  (SETQ PROJECTION_POINT1 (VLAX-CURVE-GETCLOSESTPOINTTO DFCC_DN_TRACK_CENTER INSERTION_POINT T))
  (SETQ PROJECTION_POINT2 (VLAX-CURVE-GETCLOSESTPOINTTO DFCC_UP_TRACK_CENTER INSERTION_POINT T))
  (SETQ PROJECTION_POINT3 (VLAX-CURVE-GETCLOSESTPOINTTO FORMATION_DN INSERTION_POINT T))
  (SETQ PROJECTION_POINT4 (VLAX-CURVE-GETCLOSESTPOINTTO FORMATION_UP INSERTION_POINT T))
  (SETQ LOC_NO (NTH 0 (SINGLE_ELE_LIST (EXTRACT_ATTRIBUTES (NTH I ENT_LIST) (LIST "MAST_NUMBER1" ) 1) 1)))
  (SETQ CHAINAGE (NTH 0 (SINGLE_ELE_LIST (EXTRACT_ATTRIBUTES (NTH I ENT_LIST) (LIST "CHAINAGE2" ) 1) 1)))
  (SETQ IMPLANTATION (NTH 0 (SINGLE_ELE_LIST (EXTRACT_ATTRIBUTES (NTH I ENT_LIST) (LIST "IMPLANTATION1" ) 1) 1)))
  (SETQ	TEMP_KM (SUBSTR CHAINAGE 1 (VL-STRING-POSITION (ASCII "/") CHAINAGE)))
  (SETQ	TEMP_CHAINAGE (SUBSTR CHAINAGE (+ (VL-STRING-POSITION (ASCII "/") CHAINAGE) 2)))
  (SETQ CHAINAGE (+ (* (ATOF TEMP_KM) 1000) (* (ATOF TEMP_CHAINAGE) 1)))
  (SETQ CHAINAGE (RTOS CHAINAGE 2 2))
  (SETQ TEMP_LIST (LIST LOC_NO CHAINAGE IMPLANTATION (DISTANCE2D PROJECTION_POINT1 PROJECTION_POINT2) (IF (= TRACK_FLAG "DN") "DN MAIN" "UP MAIN") (IF (= TRACK_FLAG "DN") (DISTANCE2D PROJECTION_POINT1 PROJECTION_POINT3) (DISTANCE2D PROJECTION_POINT2 PROJECTION_POINT4)) (DISTANCE2D PROJECTION_POINT3 PROJECTION_POINT4)))
  
  (SETQ FINAL_LIST (CONS TEMP_LIST FINAL_LIST))
  (SETQ I (+ I 1))
)
  (SETQ FINAL_LIST (REVERSE FINAL_LIST))
  (PUTCELLSHEET "Sheet1" (COLUMN+N START_CELL 0) (SINGLE_ELE_LIST FINAL_LIST 0))
  (PUTCELLSHEET "Sheet1" (COLUMN+N START_CELL 1) (SINGLE_ELE_LIST FINAL_LIST 1))
  (PUTCELLSHEET "Sheet1" (COLUMN+N START_CELL 2) (SINGLE_ELE_LIST FINAL_LIST 2))
  (PUTCELLSHEET "Sheet1" (COLUMN+N START_CELL 3) (SINGLE_ELE_LIST FINAL_LIST 3))
  (PUTCELLSHEET "Sheet1" (COLUMN+N START_CELL 4) (SINGLE_ELE_LIST FINAL_LIST 4))
  (PUTCELLSHEET "Sheet1" (COLUMN+N START_CELL 5) (SINGLE_ELE_LIST FINAL_LIST 5))
  (PUTCELLSHEET "Sheet1" (COLUMN+N START_CELL 6) (SINGLE_ELE_LIST FINAL_LIST 6))
  
  (SETQ LENGTH_MAST (LENGTH FINAL_LIST))
  
  
  ;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
  ;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
  ;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
  ;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
  ;;;;;;;;;;;;;;;;;;;;;;;;;;;;;;;;;;;;;;;;FOR UPLINE MASTS////////FLAG = "UP";;;;;;;;;;;;;;;;;;;;;;;;;;;;;;;;;;;;;;;;;;;;;;;;;
  (SETQ START_CELL (STRCAT "A" (ITOA (+ LENGTH_MAST 1))))
  (SETQ TRACK_FLAG "UP")
  (SETQ ENT_LIST (SINGLE_ELE_LIST (FILTER_LIST (LIST TRACK_FLAG) MAST_TTC_DIR 1) 0))
  
  
   (SETQ ENT_LIST_CHAIN (YARD_DATA_COLLECT_GPS_204 ENT_LIST '("SINGLE_CANT_MAST" "DOUBLE_CANT_MAST" "TRIPLE_CANT_MAST" "TTC" "SS0" "SS1" "SS2" "SS3" "SS4") 1 "CHAINAGE2"))
  (SETQ ENT_LIST_CHAIN (SORT_FUN (MAST_DISTANCE ENT_LIST_CHAIN) 1 1))
  (SETQ ENT_LIST (SINGLE_ELE_LIST ENT_LIST_CHAIN 0))

;(SETQ DFCC_DN_TRACK_CENTER (CAR(ENTSEL "\n SELECT DFCC DN LINE TRACK CENTER:")))
;(SETQ DFCC_UP_TRACK_CENTER (CAR(ENTSEL "\n SELECT DFCC UP LINE TRACK CENTER:")))
;(SETQ IR_TRACK_CENTER (CAR(ENTSEL "\n SELECT IR TRACK CENTER:")))
;(SETQ FORMATION_DN (CAR(ENTSEL "\n SELECT DN TRACK FORMATION:")))
;(SETQ FORMATION_UP (CAR(ENTSEL "\n SELECT UP TRACK FORMATION:")))
;(SETQ DFCC_DN_TRACK_CENTER (VLAX-ENAME->VLA-OBJECT DFCC_DN_TRACK_CENTER))
;(SETQ DFCC_UP_TRACK_CENTER (VLAX-ENAME->VLA-OBJECT DFCC_UP_TRACK_CENTER))
;(SETQ IR_TRACK_CENTER (VLAX-ENAME->VLA-OBJECT IR_TRACK_CENTER))
;(SETQ FORMATION_DN (VLAX-ENAME->VLA-OBJECT FORMATION_DN))
;(SETQ FORMATION_UP (VLAX-ENAME->VLA-OBJECT FORMATION_UP))
(SETQ I 0 MAST NIL ROTATION NIL INSERTION_POINT NIL PROJECTION_POINT1 NIL PROJECTION_POINT2 NIL PROJECTION_POINT3 NIL PROJECTION_POINT4 NIL FINAL_INSERTION_POINT NIL LOC_NO NIL CHAINAGE NIL IMPLANTATION NIL TEMP_KM NIL TEMP_CHAINAGE NIL TEMP_LIST NIL FINAL_LIST NIL)
(WHILE (< I (LENGTH ENT_LIST))
  (SETQ MAST (VLAX-ENAME->VLA-OBJECT (NTH I ENT_LIST)))
  
  (SETQ INSERTION_POINT (VLAX-SAFEARRAY->LIST (VLAX-VARIANT-VALUE (VLAX-GET-PROPERTY MAST 'INSERTIONPOINT))))
  (SETQ PROJECTION_POINT1 (VLAX-CURVE-GETCLOSESTPOINTTO DFCC_DN_TRACK_CENTER INSERTION_POINT T))
  (SETQ PROJECTION_POINT2 (VLAX-CURVE-GETCLOSESTPOINTTO DFCC_UP_TRACK_CENTER INSERTION_POINT T))
  (SETQ PROJECTION_POINT3 (VLAX-CURVE-GETCLOSESTPOINTTO FORMATION_DN INSERTION_POINT T))
  (SETQ PROJECTION_POINT4 (VLAX-CURVE-GETCLOSESTPOINTTO FORMATION_UP INSERTION_POINT T))
  (SETQ LOC_NO (NTH 0 (SINGLE_ELE_LIST (EXTRACT_ATTRIBUTES (NTH I ENT_LIST) (LIST "MAST_NUMBER1" ) 1) 1)))
  (SETQ CHAINAGE (NTH 0 (SINGLE_ELE_LIST (EXTRACT_ATTRIBUTES (NTH I ENT_LIST) (LIST "CHAINAGE2" ) 1) 1)))
  (SETQ IMPLANTATION (NTH 0 (SINGLE_ELE_LIST (EXTRACT_ATTRIBUTES (NTH I ENT_LIST) (LIST "IMPLANTATION1" ) 1) 1)))
  (SETQ	TEMP_KM (SUBSTR CHAINAGE 1 (VL-STRING-POSITION (ASCII "/") CHAINAGE)))
  (SETQ	TEMP_CHAINAGE (SUBSTR CHAINAGE (+ (VL-STRING-POSITION (ASCII "/") CHAINAGE) 2)))
  (SETQ CHAINAGE (+ (* (ATOF TEMP_KM) 1000) (* (ATOF TEMP_CHAINAGE) 1)))
  (SETQ CHAINAGE (RTOS CHAINAGE 2 2))
  (SETQ TEMP_LIST (LIST LOC_NO CHAINAGE IMPLANTATION (DISTANCE2D PROJECTION_POINT1 PROJECTION_POINT2) (IF (= TRACK_FLAG "DN") "DN MAIN" "UP MAIN") (IF (= TRACK_FLAG "DN") (DISTANCE2D PROJECTION_POINT1 PROJECTION_POINT3) (DISTANCE2D PROJECTION_POINT2 PROJECTION_POINT4)) (DISTANCE2D PROJECTION_POINT3 PROJECTION_POINT4)))
  
  (SETQ FINAL_LIST (CONS TEMP_LIST FINAL_LIST))
  (SETQ I (+ I 1))
)
  (SETQ FINAL_LIST (REVERSE FINAL_LIST))
  (PUTCELLSHEET "Sheet1" (COLUMN+N START_CELL 0) (SINGLE_ELE_LIST FINAL_LIST 0))
  (PUTCELLSHEET "Sheet1" (COLUMN+N START_CELL 1) (SINGLE_ELE_LIST FINAL_LIST 1))
  (PUTCELLSHEET "Sheet1" (COLUMN+N START_CELL 2) (SINGLE_ELE_LIST FINAL_LIST 2))
  (PUTCELLSHEET "Sheet1" (COLUMN+N START_CELL 3) (SINGLE_ELE_LIST FINAL_LIST 3))
  (PUTCELLSHEET "Sheet1" (COLUMN+N START_CELL 4) (SINGLE_ELE_LIST FINAL_LIST 4))
  (PUTCELLSHEET "Sheet1" (COLUMN+N START_CELL 5) (SINGLE_ELE_LIST FINAL_LIST 5))
  (PUTCELLSHEET "Sheet1" (COLUMN+N START_CELL 6) (SINGLE_ELE_LIST FINAL_LIST 6))
  
)






(DEFUN YARD_DATA_COLLECT_GPS_204 (ENTITY_LIST BLOCKNAME_LIST J ATTRIBUTE / LIST1 I TEMP_ELE TEMP_LIST LIST2)

  (SETQ LIST1 (SINGLE_ELE_LIST (FILTER_LIST BLOCKNAME_LIST (DATA_COLLECT_GPS ENTITY_LIST BLOCKNAME_LIST 2 -1)  0) 1))
  (SETQ I 0)
  (SETQ TEMP_ELE NIL)
  (SETQ TEMP_LIST NIL)
  (SETQ LIST2 NIL)
  (WHILE (< I (LENGTH LIST1))
    (SETQ TEMP_LIST (YARD_STRUCTURE_INFO_GPS (NTH I LIST1)))
	(SETQ A (NTH 1 (ASSOC 4 (YARD_STRUCTURE_INFO_GPS (NTH I LIST1)))))
  (SETQ TEMP_ELE (LIST (NTH 1 (ASSOC J  TEMP_LIST)) (NTH 1 (ASSOC ATTRIBUTE A))))
  (SETQ LIST2 (CONS TEMP_ELE LIST2))
    (SETQ I (+ I 1))
    )
  (REVERSE LIST2)
)



(DEFUN FILTER_LIST_CP_204 (LIST1 LIST2 POSITION / I LOOP_ELE TEMP_ELE LIST3)
  (SETQ I 0)
  (SETQ LIST3 NIL)
  (WHILE (< I (LENGTH LIST2))
    (IF (/= (NTH I LIST2) NIL)
	(PROGN
	(SETQ LOOP_ELE (NTH POSITION (NTH I LIST2)))
    (IF	(>= (VL-POSITION LOOP_ELE LIST1) 0)
      (PROGN (SETQ TEMP_ELE (NTH I LIST2))
	     (SETQ LIST3 (CONS TEMP_ELE LIST3))
      )
    )
	)
	)
    (SETQ I (+ I 1))
  )
  (SETQ LIST3 (REVERSE LIST3))
)


(DEFUN MAST_DISTANCE (LIST1)
	(SETQ I 0)
	(SETQ LIST2 NIL)
	(WHILE (< I (LENGTH LIST1))
	(SETQ TEMP_DFCC_CHAINAGE (NTH 1 (NTH I LIST1)))
	(SETQ TEMP_DFCC_KM_CHAINAGE (SUBSTR TEMP_DFCC_CHAINAGE 1 (VL-STRING-SEARCH "/" TEMP_DFCC_CHAINAGE)))
	(SETQ TEMP_DFCC_ACTUAL_CHAINAGE (SUBSTR TEMP_DFCC_CHAINAGE (+ 2 (VL-STRING-SEARCH "/" TEMP_DFCC_CHAINAGE) )))
	(SETQ DISTANCE1 (+ (* (ATOF TEMP_DFCC_KM_CHAINAGE) 1000.00) (ATOF TEMP_DFCC_ACTUAL_CHAINAGE)))
	
	(SETQ LIST2 (CONS (LIST (NTH 0 (NTH I LIST1)) DISTANCE1) LIST2))
	(SETQ I (+ I 1))
	)
	
	LIST2
	)
