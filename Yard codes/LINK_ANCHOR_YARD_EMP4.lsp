(DEFUN C:LINK_ANCHOR_YARD_EMP4()
(SETQ TOTAL_LIST_ANCHOR (ANCHOR_STRUCTURE_MAPPING_GPS_204))
(SETQ UPTRACK (CAR (ENTSEL "\n SELECT UPTRACK:")))
(SETQ DNTRACK (CAR (ENTSEL "\n SELECT DNTRACK:")))

(SETQ I 0)
(WHILE (< I (LENGTH TOTAL_LIST_ANCHOR))
(SETQ TEMP_ANC (NTH 1 (NTH I TOTAL_LIST_ANCHOR)))
(SETQ TEMP_STRUC (NTH 0 (NTH I TOTAL_LIST_ANCHOR)))

(SETQ TRACK_TYPE (CADR (CAR (anchor_up_dn (BUILD_LIST (ENTITY_DFX (list TEMP_ANC) 10 -1) (LIST 0 1)) UPTRACK DNTRACK))))
(SETQ FLIP1 (CADR (CAR (GET_DYNAMIC_PROPERTIES TEMP_ANC (LIST "ANF1")))))

(setq eff_name (effective_name TEMP_STRUC) )
(if (= eff_name "PORTAL")
(PROGN 
(SETQ loc1 (NTH 1 (ASSOC "MAST_NUMBER1" (GET_ATTRIBUTES TEMP_STRUC))))
(SETQ loc2 (NTH 1 (ASSOC "MAST_NUMBER2" (GET_ATTRIBUTES TEMP_STRUC))))
(setq chain1 (NTH 1 (ASSOC "CHAINAGE1" (GET_ATTRIBUTES TEMP_STRUC))))
)

(PROGN 
(if (= eff_name "SS0")
(PROGN 
(SETQ loc1 (NTH 1 (ASSOC "MAST_NUMBER1" (GET_ATTRIBUTES TEMP_STRUC))))
(setq loc2 loc1)
(setq chain1 (NTH 1 (ASSOC "CHAINAGE1" (GET_ATTRIBUTES TEMP_STRUC))))
)
(PROGN
(SETQ loc1 (NTH 1 (ASSOC "MAST_NUMBER1" (GET_ATTRIBUTES TEMP_STRUC))))
(setq loc2 loc1)
(setq chain1 (NTH 1 (ASSOC "CHAINAGE1" (GET_ATTRIBUTES TEMP_STRUC))))
)
)
)
)



(if (= track_type "DN")
        
        (MODIFY_ATTRIBUTES TEMP_ANC (LIST "ANCHOR_NATURE1" "ANCHOR_FOUNDATION1") (LIST LOC1 CHAIN1))       
        (MODIFY_ATTRIBUTES TEMP_ANC (LIST "ANCHOR_NATURE1" "ANCHOR_FOUNDATION1") (LIST LOC2 CHAIN1))       
        
		
		
  )

(SETQ I (+ I 1))
)


)





(DEFUN PORTAL_END_POINTS_GPS_204 (LIST1 / I ENAME TEMP_ELE LIST2)
  (SETQ I 0)
  (SETQ ENAME NIL)
  (SETQ TEMP_ELE NIL)
  (SETQ LIST2 NIL)
  (WHILE (< I (LENGTH LIST1))
    (SETQ ENAME (NTH I LIST1))
	(SETQ ROTATION (VLAX-GET-PROPERTY (VLAX-ENAME->VLA-OBJECT ENAME) 'ROTATION))
    
	(SETQ PORTAL_OTHER_POINT (POLAR (NTH 1 (ASSOC 3 (YARD_STRUCTURE_INFO_GPS ENAME))) (+ (* 1 (/ PI 2)) ROTATION) (NTH 1 (NTH 0 (GET_DYNAMIC_PROPERTIES ENAME (LIST "STL1"))))))
	; (SETQ
      ; TEMP_ELE (SUM_LIST (NTH 1 (ASSOC 3 (YARD_STRUCTURE_INFO_GPS ENAME)))
			 ; (BLOCK_REFERENCE_LENGTHS (VLAX-GET-PROPERTY (VLAX-ENAME->VLA-OBJECT ENAME) 'EFFECTIVENAME) ENAME)
	       ; )
    ; )
	(SETQ TEMP_ELE (LIST (NTH 1 (ASSOC 3 (YARD_STRUCTURE_INFO_GPS ENAME))) PORTAL_OTHER_POINT))
    (SETQ TEMP_ELE (LIST (LIST ENAME (NTH 0 TEMP_ELE))
			 (LIST ENAME (NTH 1 TEMP_ELE))
		   )
    )
    (SETQ LIST2 (CONS TEMP_ELE LIST2))
    (SETQ I (+ I 1))
  )
  (REVERSE LIST2)
)


(DEFUN ANCHOR_STRUCTURE_MAPPING_GPS_204	(/
				 WPT1
				 WPT2
				 MAST_TTC
				 PORTAL_ENTITIES
				 PORTAL_ENDS
				 PORTAL_END_UP
				 PORTAL_END_DN
				 PORTAL_END_UP_DN
				 MAST_PORTAL_TTC
				 ANCHOR_LIST
				 ANCHOR_STRUCTURE_MAP_DATA
				)
  (SETQ WPT1 (GETPOINT "ENTER STARTING POINT IN LOP"))
  (SETQ WPT2 (GETPOINT "\n ENTER ENDING POINT IN LOP"))
  (SETQ BLOCKS_LIST (FORM_SSSET (SSGET "W" WPT1 WPT2  (LIST (CONS 0 "INSERT")))))
  (SETQ	MAST_ENTITIES
	 (YARD_DATA_COLLECT_GPS
	   BLOCKS_LIST
	   '("SINGLE_CANT_MAST"			 "DOUBLE_CANT_MAST"
	     "TRIPLE_CANT_MAST"			 "TTC"
	     "SS1"	       "SS2"		 "SS3"
	     "SS4"
	    )
	   1
	   5
	 )
  )
  
  (SETQ UPLINE_MAST_ENTITIES (FILTER_LIST '("DN") MAST_ENTITIES 1))
  (SETQ DNLINE_MAST_ENTITIES (FILTER_LIST '("UP") MAST_ENTITIES 1))
  (SETQ	UPLINE_MAST_ENTITIES
	 (EXTRACT_ENTITY_INFO
	   (SINGLE_ELE_LIST UPLINE_MAST_ENTITIES 0)
	   1
	   3
	 )
  )
  (SETQ	DNLINE_MAST_ENTITIES
	 (EXTRACT_ENTITY_INFO
	   (SINGLE_ELE_LIST DNLINE_MAST_ENTITIES 0)
	   1
	   3
	 )
  )
  (SETQ	PORTAL_ENTITIES
	 (YARD_DATA_COLLECT_GPS BLOCKS_LIST '("PORTAL" "SS5") 1 3) 
  )
  (SETQ TTC_ENTITIES (YARD_DATA_COLLECT_GPS BLOCKS_LIST '("TTC" "SS4") 1 3))
  (SETQ BUFFER_END_ENTITIES (YARD_DATA_COLLECT_GPS BLOCKS_LIST '("SS0") 1 3))

  ;;***************NEWLY ADDED********************************************************************************************************************;--->START
					;(SETQ MAST_ENTITIES (YARD_DATA_COLLECT WPT1 WPT2 '("SINGLE_CANT_MAST" "DOUBLE_CANT_MAST" "TRIPLE_CANT_MAST" "TTC" "SS0" "SS1" "SS2" "SS3" "SS4") 1 3))
					;(SETQ PORTAL_ENTITIES (YARD_DATA_COLLECT WPT1 WPT2 '("PORTAL" "SS5") 1 3))
					;(SETQ PORTAL_ENDS (PORTAL_END_POINTS (SINGLE_ELE_LIST PORTAL_ENTITIES 0)))
					;(SETQ PORTAL_END_UP (SINGLE_ELE_LIST PORTAL_ENDS 0))
					;(SETQ PORTAL_END_DN (SINGLE_ELE_LIST PORTAL_ENDS 1))
					;(SETQ PORTAL_END_UP_DN (BUILD_LIST (ADD_LISTS PORTAL_END_UP PORTAL_END_DN) '(0 1 3)))
					;(SETQ MAST_WITH_LOC_NO (BUILD_LIST (ATTRIBUTES_FROM_ENTITIES MAST_ENTITIES "MAST_NUMBER1" 0) '(2 0 1)))
					;(SETQ PORTAL_WITH_LOC_NO (BUILD_LIST (ATTRIBUTES_FROM_ENTITIES PORTAL_END_UP_DN "MAST_NUMBER1" 0) '(3 0 1 2)) )
					;(SETQ WITH_LOC_NO (APPEND MAST_WITH_LOC_NO PORTAL_WITH_LOC_NO))
					;(SETQ WITH_LOC_NO (SORT_FUN WITH_LOC_NO 0 0))
					;(SETQ TOTAL_STRUCTURE_ENTITIES (REMOVE_NTH_ELE WITH_LOC_NO 0))
  ;;***************NEWLY ADDED********************************************************************************************************************;--->END

  (SETQ	CANTI_LIST
	 (YARD_DATA_COLLECT_GPS
            BLOCKS_LIST
	   '("SINGLE_CANT_MAST"	    "SINGLE_CANT_DA"
	     "DOUBLE_CANT_MAST"	    "DOUBLE_CANT_DA"
	     "TRIPLE_CANT_MAST"	    "TRIPLE_CANT_DA"
	     "SINGLE_CANT_UPRIGHT"  "DOUBLE_CANT_UPRIGHT"
	     "TRIPLE_CANT_UPRIGHT"  "SS0"
	     "SS1"		    "SS2"
	     "SS3"		    "BOX_TYPE"
	    )
	   1
	   3
	 )
  )
  (SETQ	MAST_TTC (YARD_DATA_COLLECT_GPS
                  BLOCKS_LIST
		   '("SINGLE_CANT_MAST"
		     "DOUBLE_CANT_MAST"
		     "TRIPLE_CANT_MAST"		       "TTC"
		     "SS0"	      "SS1"	       "SS2"
		     "SS3"	      "SS4"
		    )
		   1
		   3
		 )
  )
  (SETQ	MAST_E (YARD_DATA_COLLECT_GPS
                 BLOCKS_LIST
		 '("SINGLE_CANT_MAST" "DOUBLE_CANT_MAST"
		   "TRIPLE_CANT_MAST" "SS0"
		   "SS1"	      "SS2"
		   "SS3"
		  )
		 1
		 3
	       )
  )
  (SETQ	PORTAL_ENDS
	 (PORTAL_END_POINTS_GPS_204 (SINGLE_ELE_LIST PORTAL_ENTITIES 0))
  )
  (SETQ PORTAL_END_UP (SINGLE_ELE_LIST PORTAL_ENDS 0))
  (SETQ PORTAL_END_DN (SINGLE_ELE_LIST PORTAL_ENDS 1))
  (SETQ	PORTAL_END_UP_DN
	 (BUILD_LIST
	   (ADD_LISTS PORTAL_END_UP PORTAL_END_DN)
	   '(0 1 3)
	 )
  )
  (SETQ MAST_PORTAL_TTC (APPEND MAST_TTC PORTAL_END_UP PORTAL_END_DN))
  (SETQ	ANCHOR_LIST
	 (YARD_DATA_COLLECT_GPS BLOCKS_LIST '("ANCHOR" "BTB_ANC") 1 3)
  )
  (SETQ	ANCHOR_STRUCTURE_MAP_DATA
	 (DATA_TO_STRUCTURE_MAP1
	   ANCHOR_LIST
	   MAST_PORTAL_TTC
	   1
	   1
	 )
  )
  (SETQ	ANCHOR_STRUCTURE_MAP_DATA
	 (BUILD_LIST
	   ANCHOR_STRUCTURE_MAP_DATA
	   '(1 0)
	 )
  )
)




(DEFUN COLOR_CHANGE_1 (AA / M)
(SETQ M 0)
(WHILE (< M (LENGTH AA))
(CHANGE_COLOR (NTH 0 (NTH M AA)))
(CHANGE_COLOR (NTH 1 (NTH M AA)))


(SETQ M (+ M 1))
)
)
